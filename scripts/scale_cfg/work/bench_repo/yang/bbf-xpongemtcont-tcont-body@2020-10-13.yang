submodule bbf-xpongemtcont-tcont-body {
  yang-version 1.1;
  belongs-to bbf-xpongemtcont {
    prefix bbf-xpongemtcont;
  }

  import ietf-interfaces {
    prefix if;
  }
  import bbf-xpon-if-type {
    prefix bbf-xponift;
  }
  import bbf-yang-types {
    prefix bbf-yang;
  }


  include "bbf-xpongemtcont-base";

  include "bbf-xpongemtcont-traffic-descriptor-profile-body";

  organization
    "Broadband Forum <https://www.broadband-forum.org>
     Fiber Access Networks Work Area";
  contact
    "Comments or questions about this Broadband Forum YANG module
     should be directed to <mailto:info@broadband-forum.org>.

     Editor:      Joey Boyd, ADTRAN

     Editor:      Igor Ternovsky, Broadcom

     Editor:      Robert Peschi, Nokia

     WA Director: Marta Seda, Calix

     WA Director: Samuel Chen, Broadcom";
  description
    "This submodule contains a collection of YANG definitions for
     managing Transmission Containers (T-CONT).

     Copyright (c) 2018-2020, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i2; see
     the TR itself for full legal notices.";

  revision 2020-10-13 {
    description
      "Issue 2.
       * Approval Date:    2020-10-13.
       * Publication Date: 2020-10-13.";
    reference
      "TR-385i2: ITU-T PON YANG Modules
               <https://www.broadband-forum.org/technical/download/
                        TR-385_Issue-2.pdf>";
  }
  revision 2019-02-25 {
    description
      "Initial revision.
       * Approval Date:    2019-02-25.
       * Publication Date: 2019-02-25.";
    reference
      "TR-385: ITU-T PON YANG Modules
               <https://www.broadband-forum.org/technical/download/
                        TR-385.pdf>";
  }

  feature configurable-alloc-id {
    description
      "Indicates support for configuration of the Allocation
       Identifier (Alloc-ID).";
  }

  typedef alloc-id {
    type uint16;
    description
      "Transmission Container (T-CONT) Allocation Identifier
       (Alloc-ID). For G-PON the value should be in [256..4095] and
       for XG-PON, XGS-PON and NG-PON2 it should be in
       [1024..16383].";
    reference
      "ITU-T G.984.3 clause 5.5.3
       ITU-T G.987.3 clause 6.4.3
       ITU-T G.9807.1 clause C.6.1.5.7
       ITU-T G.989.3 clause 6.1.5.7";
  }

  grouping tconts-config-data {
    description
      "The configuration data for all Transmission Containers
       (T-CONT).";
    list tcont {
      key "name";
      description
        "List of Transmission Containers (T-CONT).";
      leaf name {
        type bbf-yang:string-ascii64;
        description
          "Name of the Transmission Container (T-CONT).";
      }
      leaf alloc-id {
        if-feature "bbf-xpongemtcont:configurable-alloc-id";
        type alloc-id;
        description
          "Transmission Container (T-CONT) Allocation Identifier
           (Alloc-ID). When configured this is the value which must
           actually be used between the Optical Line Termination (OLT)
           device and Optical Network Unit (ONU) device for this
           T-CONT. For G-PON the value should be in [256..4095] and
           for XG-PON, XGS-PON and NG-PON2 it should be in
           [1024..16383].";
        reference
          "ITU-T G.984.3 clause 5.5.3
           ITU-T G.987.3 clause 6.4.3
           ITU-T G.9807.1 clause C.6.1.5.7
           ITU-T G.989.3 clause 6.1.5.7";
      }
      leaf interface-reference {
        type if:interface-ref;
        must "derived-from-or-self(/if:interfaces/if:interface[if:name=current()]/if:type,'bbf-xponift:v-ani') or derived-from-or-self(/if:interfaces/if:interface[if:name=current()]/if:type,'bbf-xponift:ani')" {
          error-message
            "Must reference an interface of type 'v-ani' or 'ani'.";
        }
        description
          "Reference to 'v-ani' or 'ani' type interface.";
      }
      leaf traffic-descriptor-profile-ref {
        type leafref {
          path "/bbf-xpongemtcont:xpongemtcont/bbf-xpongemtcont:traffic-descriptor-profiles/bbf-xpongemtcont:traffic-descriptor-profile/bbf-xpongemtcont:name";
        }
        description
          "References an existing traffic descriptor profile.";
      }
    }
  }

  grouping tconts-state-data {
    description
      "The state data for all Transmission Containers (T-CONT).";
    list tcont {
      key "name";
      description
        "List of Transmission Containers (T-CONT).";
      leaf name {
        type bbf-yang:string-ascii64;
        description
          "Name of the Transmission Container (T-CONT).";
      }
      leaf actual-alloc-id {
        type alloc-id;
        description
          "Transmission Container (T-CONT) Allocation Identifier
           (Alloc-ID). This is the value which is actually used
           between the Optical Line Termination (OLT) device and
           Optical Network Unit (ONU) device for this T-CONT.";
        reference
          "ITU-T G.984.3 clause 5.5.3
           ITU-T G.987.3 clause 6.4.3
           ITU-T G.9807.1 clause C.6.1.5.7
           ITU-T G.989.3 clause 6.1.5.7";
      }
    }
  }

  augment "/bbf-xpongemtcont:xpongemtcont" {
    description
      "Augment the xPON G-PON Encapsulation Method (GEM) port and
       Transmission Container (T-CONT) configuration with T-CONT
       specific configuration.";
    container tconts {
      description
        "Transmission Container (T-CONT) configuration data.";
      uses tconts-config-data;
    }
  }
  augment "/bbf-xpongemtcont:xpongemtcont-state" {
    description
      "Augment the xPON G-PON Encapsulation Method (GEM) port and
       Transmission Container (T-CONT) state data with T-CONT specific
       state data.";
    container tconts {
      description
        "Transmission Container (T-CONT) state data.";
      uses tconts-state-data;
    }
  }
}
