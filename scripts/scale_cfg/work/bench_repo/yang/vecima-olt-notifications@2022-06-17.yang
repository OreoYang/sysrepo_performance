module vecima-olt-notifications {
  yang-version 1.1;
  namespace "urn:vecima:yang:vecima-olt-notifications";
  prefix vcm-olt-notif;

  organization
    "Vecima Networks Inc.";
  contact
    "https://www.vecima.com";
  description
    "This YANG module defines notifications generated by
     remote/shelf olt devices.";

  revision 2022-06-17 {
    description
      "Initial version.";
    reference
      "";
  }

  typedef severity-type {
    type enumeration {
      enum "cleared" {
        value 1;
        description
          "The cleared enum value";
      }
      enum "information" {
        value 2;
        description
          "The information enum value";
      }
      enum "indeterminate" {
        value 3;
        description
          "The indeterminate enum value";
      }
      enum "minor" {
        value 4;
        description
          "The minor enum value";
      }
      enum "warning" {
        value 5;
        description
          "The warning enum value";
      }
      enum "major" {
        value 6;
        description
          "The major enum value";
      }
      enum "critical" {
        value 7;
        description
          "The critical enum value";
      }
    }
    description
      "Severity of an alarm, including the cleared state";
  }

  typedef support-info-reason-type {
    type enumeration {
      enum "sp-periodic" {
        value 0;
        description
          "The sp-periodic enum value";
      }
      enum "sp-on-demand" {
        value 1;
        description
          "The sp-on-demand enum value";
      }
      enum "sp-process-exit" {
        value 2;
        description
          "The sp-process-exit enum value";
      }
      enum "sp-wd-timeout" {
        value 3;
        description
          "The sp-wd-timeout enum value";
      }
      enum "sp-kernel-panic" {
        value 4;
        description
          "The sp-kernel-panic enum value";
      }
      enum "sp-ac-fail" {
        value 5;
        description
          "The sp-ac-fail enum value";
      }
      enum "sp-lag-fail" {
        value 6;
        description
          "The sp-lag-fail enum value";
      }
    }
    description
      "";
  }

  typedef support-info-upload-result-type {
    type enumeration {
      enum "success" {
        value 0;
        description
          "The success enum value";
      }
      enum "failure" {
        value 1;
        description
          "The failure enum value";
      }
    }
    description
      "The type of support-info-upload-result";
  }

  grouping common-event-group {
    description
      "The common event group";
    leaf ifname {
      type string;
      description
        "The specific interface on the device which generated the
         event.";
    }
    leaf event-info {
      type string;
      description
        "info";
    }
  }

  grouping common-alarm-group {
    description
      "The comon alarm group";
    leaf ifname {
      type string;
      description
        "The specific interface on the device which generated the
         alarm.";
    }
    leaf severity {
      type severity-type;
      description
        "The severity type";
    }
    leaf specific-problem {
      type string;
      description
        "The specific problem on the managed object.";
    }
    leaf alarm-text {
      type string;
      description
        "Text to be presented to the operator.";
    }
  }

  notification support-info-done {
    description
      "The support-info-done notification";
    uses common-event-group;
    leaf support-info-reason-code {
      type support-info-reason-type;
      description
        "reason for support info generated";
    }
  }
  notification support-info-upload-done {
    description
      "The support-info-upload-done notification";
    uses common-event-group;
    leaf support-info-upload-reason-code {
      type support-info-reason-type;
      description
        "reason for support info generated";
    }
    leaf support-info-upload-result {
      type support-info-upload-result-type;
      description
        "support info upload result";
    }
  }
  notification sw-process-exit {
    description
      "The sw-process-exit notification";
    uses common-alarm-group;
  }
}
