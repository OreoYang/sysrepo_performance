module bbf-onu-xpon-metadata-common {
  yang-version 1.1;
  namespace "urn:bbf:yang:bbf-onu-xpon-metadata-common";
  prefix bbf-onuxpon-metac;

  import bbf-xpon-types {
    prefix bbf-xpon-types;
  }

  organization
    "Broadband Forum <https://www.broadband-forum.org>
     Fiber Access Networks Work Area";
  contact
    "Comments or questions about this Broadband Forum YANG module
     should be directed to <mailto:info@broadband-forum.org>.

     Editor:      Joey Boyd, Adtran

     Editor:      Robert Peschi, Nokia

     PS Leader:   Joey Boyd, Adtran

     WA Director: Marta Seda, Calix";
  description
    "This module contains a collection of YANG definitions for
     supporting the Broadband Forum requirements on the management of
     Optical Network Units (ONUs).

     Specifically, this module defines grouping containing xPON
     metadata for the management of the Optical Network Unit (ONU).

     Copyright (c) 2018-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-505; see
     the WT itself for full legal notices.";

  revision 2024-01-04 {
    description
      "TBD.
       * Approval Date:    TBD.
       * Publication Date: TBD.";
    reference
      "TBD";
  }

  grouping xpon-metadata-config {
    description
      "Configuration metadata intended for the Optical Network
       Unit (ONU) physical device. This is data about the ONU,
       available to the ONU Manager for its own purpose.
       The ONU manager does not configure this data to the ONU.";
    leaf xpon-type {
      type identityref {
        base bbf-xpon-types:channel-pair-type-base;
      }
      description
        "The expected xPON type of the ONU (e.g., TWDM HSP,
         TDM HSP, 25GS-PON, TWDM NG-PON2, PtP NG-PON2, XGS-PON,
         XG-PON, GPON). This data node could be used for
         instance to help the ONU manager to validate the
         ranges of configured Transmission Convergence (TC),
         such as GPON Encapsulation Method (GEM) port ID and
         Allocation Identifier (Alloc-ID).";
      reference
        "ITU-T G.9804.2;
         MSA 25GS-PON;
         ITU-T G.989.3;
         ITU-T G.9807.1;
         ITU-T G.987.3;
         ITU-T G.984.3";
    }
  }
}
