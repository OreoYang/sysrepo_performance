module bbf-ldra {
  yang-version 1.1;
  namespace "urn:bbf:yang:bbf-ldra";
  prefix bbf-ldra;

  import ietf-interfaces {
    prefix if;
  }
  import ietf-yang-types {
    prefix yang;
  }
  import bbf-if-type {
    prefix bbfift;
  }
  import bbf-ldra-profile-common {
    prefix bbf-ldra-pc;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on subscriber
     management via the DHCPv6 protocol as applicable to access
     network equipment. As such, this module is specific to access
     network equipment (e.g., BBF-specified Access Nodes and FTTdp
     DPUs).

     This functionality is also known as a Lightweight DHCPv6 Relay
     Agent (LDRA).

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a7; see
     the TR itself for full legal notices.";

  revision 2023-12-15 {
    description
      "Amendment 7.
       * Approval Date:    2023-12-15.
       * Publication Date: 2023-12-15.";
    reference
      "TR-383a7: Common YANG Modules
                 <https://www.broadband-forum.org/technical/download/
                          TR-383_Amendment-7.pdf>";
  }
  revision 2023-03-07 {
    description
      "Amendment 6.
       * Approval Date:    2023-03-07.
       * Publication Date: 2023-03-07.";
    reference
      "TR-383a6: Common YANG Modules
                 <https://www.broadband-forum.org/technical/download/
                          TR-383_Amendment-6.pdf>";
  }
  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }
  revision 2018-07-13 {
    description
      "Amendment 1.
       * Approval Date:    2018-06-04.
       * Publication Date: see revision date above.";
    reference
      "TR-383: Common YANG Modules
               <https://www.broadband-forum.org/technical/download/
                        TR-383_Amendment-1.pdf>";
  }
  revision 2017-05-08 {
    description
      "Initial revision.
       * Approval Date:    see revision date above.
       * Publication Date: 2017-06-02.";
    reference
      "TR-383: Common YANG Modules
               <https://www.broadband-forum.org/technical/download/
                        TR-383.pdf>";
  }

  uses bbf-ldra-pc:dhcpv6-ldra-profiles;

  augment "/if:interfaces/if:interface" {
    when "derived-from-or-self(if:type,'bbfift:vlan-sub-interface')" {
      description
        "Applies only to VLAN sub-interfaces.";
    }
    description
      "Lightweight DHCPv6 Relay Agent (LDRA) configuration per VLAN
       sub-interface.";
    container dhcpv6-ldra {
      presence "Enables the management of DHCPv6 message processing at this
       VLAN sub-interface.";
      description
        "LDRA configuration parameters.

         The presence of the container itself does not instantiate a
         LDRA, this is dependent on the value of the contained leaf
         'enable'.

         If the container is not present, no LDRA functionality is
         performed on this interface. Any received DHCPv6 messages are
         processed based on the layer 2 forwarding configuration,
         e.g., VLAN sub-interface and/or layer 2 forwarding.";
      leaf enable {
        type boolean;
        default "false";
        description
          "Controls the LDRA processing of DHCPv6 messages received on
           an interface and messages to be sent to an interface.

           If 'true', enables the LDRA to process DHCPv6 messages
           based on the additional relay agent configuration.

           If 'false', no LDRA functionality is performed. Any
           received DHCPv6 messages are processed based on the layer 2
           forwarding configuration, e.g., VLAN sub-interface and/or
           layer 2 forwarding.";
      }
      leaf trusted-port {
        type boolean;
        default "false";
        description
          "Marks a client-facing interface as trusted for the LDRA.
           When a client-facing interface is deemed untrusted, i.e.,
           configured 'false', then the LDRA must discard any message
           of type RELAY-FORW (12) received from the client-facing
           interface. When an interface is trusted i.e., configured
           'true', then the RELAY-FORW DHCPv6 message coming from an
           LDRA, or other messages coming from a client such as a
           Solicit message, are forwarded embedded in a new RELAY-FORW
           message.";
        reference
          "RFC 6221 Section 6.1.2";
      }
      leaf profile-ref {
        when "../enable = 'true'" {
          description
            "Applicable only when LDRA functionality is enabled.";
        }
        type leafref {
          path "/bbf-ldra:dhcpv6-ldra-profiles/bbf-ldra:dhcpv6-ldra-profile/bbf-ldra:name";
        }
        mandatory true;
        description
          "Reference to the DHCPv6 configuration profile.";
      }
    }
  }
  augment "/if:interfaces-state/if:interface/if:statistics" {
    when "derived-from-or-self (../if:type,
     'bbfift:vlan-sub-interface')" {
      description
        "Applies only to VLAN sub-interfaces and only when the LDRA
         functionality is enabled.";
    }
    description
      "Lightweight DHCPv6 Relay Agent (LDRA) statistics.";
    container dhcpv6-ldra {
      presence "LDRA functionality is enabled and LDRA statistics are
       available.";
      description
        "A container presents the message statistics related to the
         LDRA.";
      leaf in-bad-packets-from-client {
        type yang:counter32;
        units "messages";
        description
          "Bad DHCPv6 messages received on the interface. The messages
           are received from a DHCPv6 Client connected to it (directly
           or indirectly through a network).

           Discontinuities in the counter can occur at
           re-initialization of the management system, and/or when the
           LDRA functionality is disabled/enabled.";
      }
      leaf in-bad-packets-from-server {
        type yang:counter32;
        units "messages";
        description
          "Bad DHCPv6 messages received on the interface. The messages
           are received from a DHCPv6 Server connected to it (directly
           or indirectly through a network).

           Discontinuities in the counter can occur at
           re-initialization of the management system, and/or when the
           LDRA functionality is disabled/enabled.";
      }
      leaf option-17-inserted-packets-to-server {
        type yang:counter32;
        units "messages";
        description
          "DHCPv6 messages from a Client to a Server that passed this
           interface and for which the LDRA did insert option 17.

           Discontinuities in the counter can occur at
           re-initialization of the management system, and/or when the
           LDRA functionality is disabled/enabled.";
      }
      leaf option-17-removed-packets-to-client {
        type yang:counter32;
        units "messages";
        description
          "DHCPv6 messages from a Server to a Client that passed this
           interface and for which the LDRA did remove
           option 17.

           Discontinuities in the counter can occur at
           re-initialization of the management system, and/or when the
           LDRA functionality is disabled/enabled.";
      }
      leaf option-18-inserted-packets-to-server {
        type yang:counter32;
        units "messages";
        description
          "DHCPv6 messages from a Client to a Server that passed this
           interface and for which the LDRA did insert
           option 18.

           Discontinuities in the counter can occur at
           re-initialization of the management system, and/or when the
           LDRA functionality is disabled/enabled.";
      }
      leaf option-18-removed-packets-to-client {
        type yang:counter32;
        units "messages";
        description
          "DHCPv6 messages from a Server to a Client that passed this
           interface and for which the LDRA did remove option 18.

           Discontinuities in the counter can occur at
           re-initialization of the management system, and/or when the
           LDRA functionality is disabled/enabled.";
      }
      leaf option-37-inserted-packets-to-server {
        type yang:counter32;
        units "messages";
        description
          "DHCPv6 messages from a Client to a Server that passed this
           interface and for which the LDRA did insert
           option 37.

           Discontinuities in the counter can occur at
           re-initialization of the management system, and/or when the
           LDRA functionality is disabled/enabled.";
      }
      leaf option-37-removed-packets-to-client {
        type yang:counter32;
        units "messages";
        description
          "DHCPv6 messages from a Server to a Client that passed this
           interface and for which the LDRA did remove
           option 37.

           Discontinuities in the counter can occur at
           re-initialization of the management system, and/or when the
           LDRA functionality is disabled/enabled.";
      }
      leaf outgoing-mtu-exceeded-packets-from-client {
        type yang:counter32;
        units "messages";
        description
          "DHCPv6 messages from a Client that are dropped because the
           Relay-Message size after adding the options would exceed
           the MTU of the outgoing interface.

           Discontinuities in the counter can occur at
           re-initialization of the management system, and/or when the
           LDRA functionality is disabled/enabled.";
        reference
          "RFC 6221 Section 5.3.1";
      }
    }
  }
}
