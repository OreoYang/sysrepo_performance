module iana-ssh-key-exchange-algs {
  yang-version 1.1;
  namespace "urn:ietf:params:xml:ns:yang:iana-ssh-key-exchange-algs";
  prefix sshkea;

  organization
    "Internet Assigned Numbers Authority (IANA)";
  contact
    "Postal: ICANN
             12025 Waterfront Drive, Suite 300
             Los Angeles, CA  90094-2536
             United States of America
     Tel:    +1 310 301 5800
     Email:  iana@iana.org";
  description
    "This module defines identities for the key exchange algorithms
     defined in the 'Key Exchange Method Names' sub-registry of the
     'Secure Shell (SSH) Protocol Parameters' registry maintained
     by IANA.

     Copyright (c) 2022 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     The initial version of this YANG module is part of RFC EEEE
     (https://www.rfc-editor.org/info/rfcEEEE); see the RFC
     itself for full legal notices.";

  revision 2022-06-16 {
    description
      "Reflects contents of the key exchange algorithms registry
       on June 16, 2022.";
    reference
      "RFC EEEE: YANG Groupings for SSH Clients and SSH Servers";
  }

  identity key-exchange-alg-base {
    description
      "Base identity used to identify key exchange algorithms.";
  }

  identity diffie-hellman-group-exchange-sha1 {
    base key-exchange-alg-base;
    status deprecated;
    description
      "DIFFIE-HELLMAN-GROUP-EXCHANGE-SHA1";
    reference
      "RFC 4419:
         Diffie-Hellman Group Exchange for the
         Secure Shell (SSH) Transport Layer Protocol";
  }

  identity diffie-hellman-group-exchange-sha256 {
    base key-exchange-alg-base;
    description
      "DIFFIE-HELLMAN-GROUP-EXCHANGE-SHA256";
    reference
      "RFC 4419:
         Diffie-Hellman Group Exchange for the
         Secure Shell (SSH) Transport Layer Protocol";
  }

  identity diffie-hellman-group1-sha1 {
    base key-exchange-alg-base;
    status deprecated;
    description
      "DIFFIE-HELLMAN-GROUP1-SHA1";
    reference
      "RFC 4253:
         The Secure Shell (SSH) Transport Layer Protocol";
  }

  identity diffie-hellman-group14-sha1 {
    base key-exchange-alg-base;
    status deprecated;
    description
      "DIFFIE-HELLMAN-GROUP14-SHA1";
    reference
      "RFC 4253:
         The Secure Shell (SSH) Transport Layer Protocol";
  }

  identity diffie-hellman-group14-sha256 {
    base key-exchange-alg-base;
    status deprecated;
    description
      "DIFFIE-HELLMAN-GROUP14-SHA256";
    reference
      "RFC 8268:
         More Modular Exponentiation (MODP) Diffie-Hellman (DH)
         Key Exchange (KEX) Groups for Secure Shell (SSH)";
  }

  identity diffie-hellman-group15-sha512 {
    base key-exchange-alg-base;
    description
      "DIFFIE-HELLMAN-GROUP15-SHA512";
    reference
      "RFC 8268:
         More Modular Exponentiation (MODP) Diffie-Hellman (DH)
         Key Exchange (KEX) Groups for Secure Shell (SSH)";
  }

  identity diffie-hellman-group16-sha512 {
    base key-exchange-alg-base;
    description
      "DIFFIE-HELLMAN-GROUP16-SHA512";
    reference
      "RFC 8268:
         More Modular Exponentiation (MODP) Diffie-Hellman (DH)
         Key Exchange (KEX) Groups for Secure Shell (SSH)";
  }

  identity diffie-hellman-group17-sha512 {
    base key-exchange-alg-base;
    description
      "DIFFIE-HELLMAN-GROUP17-SHA512";
    reference
      "RFC 8268:
         More Modular Exponentiation (MODP) Diffie-Hellman (DH)
         Key Exchange (KEX) Groups for Secure Shell (SSH)";
  }

  identity diffie-hellman-group18-sha512 {
    base key-exchange-alg-base;
    description
      "DIFFIE-HELLMAN-GROUP18-SHA512";
    reference
      "RFC 8268:
         More Modular Exponentiation (MODP) Diffie-Hellman (DH)
         Key Exchange (KEX) Groups for Secure Shell (SSH)";
  }

  identity ecdh-sha2-nistp256 {
    base key-exchange-alg-base;
    status deprecated;
    description
      "ECDH-SHA2-NISTP256 (secp256r1)";
    reference
      "RFC 5656:
         Elliptic Curve Algorithm Integration in the
         Secure Shell Transport Layer";
  }

  identity ecdh-sha2-nistp384 {
    base key-exchange-alg-base;
    description
      "ECDH-SHA2-NISTP384 (secp384r1)";
    reference
      "RFC 5656:
         Elliptic Curve Algorithm Integration in the
         Secure Shell Transport Layer";
  }

  identity ecdh-sha2-nistp521 {
    base key-exchange-alg-base;
    description
      "ECDH-SHA2-NISTP521 (secp521r1)";
    reference
      "RFC 5656:
         Elliptic Curve Algorithm Integration in the
         Secure Shell Transport Layer";
  }

  identity ecdh-sha2-1.3.132.0.1 {
    base key-exchange-alg-base;
    description
      "ECDH-SHA2-1.3.132.0.1 (nistk163, sect163k1)";
    reference
      "RFC 5656:
         Elliptic Curve Algorithm Integration in the
         Secure Shell Transport Layer";
  }

  identity ecdh-sha2-1.2.840.10045.3.1.1 {
    base key-exchange-alg-base;
    description
      "ECDH-SHA2-1.2.840.10045.3.1.1 (nistp192, secp192r1)";
    reference
      "RFC 5656:
         Elliptic Curve Algorithm Integration in the
         Secure Shell Transport Layer";
  }

  identity ecdh-sha2-1.3.132.0.33 {
    base key-exchange-alg-base;
    description
      "ECDH-SHA2-1.3.132.0.33 (nistp224, secp224r1)";
    reference
      "RFC 5656:
         Elliptic Curve Algorithm Integration in the
         Secure Shell Transport Layer";
  }

  identity ecdh-sha2-1.3.132.0.26 {
    base key-exchange-alg-base;
    description
      "ECDH-SHA2-1.3.132.0.26 (nistk233, sect233k1)";
    reference
      "RFC 5656:
         Elliptic Curve Algorithm Integration in the
         Secure Shell Transport Layer";
  }

  identity ecdh-sha2-1.3.132.0.27 {
    base key-exchange-alg-base;
    description
      "ECDH-SHA2-1.3.132.0.27 (nistb233, sect233r1)";
    reference
      "RFC 5656:
         Elliptic Curve Algorithm Integration in the
         Secure Shell Transport Layer";
  }

  identity ecdh-sha2-1.3.132.0.16 {
    base key-exchange-alg-base;
    description
      "ECDH-SHA2-1.3.132.0.16 (nistk283, sect283k1)";
    reference
      "RFC 5656:
         Elliptic Curve Algorithm Integration in the
         Secure Shell Transport Layer";
  }

  identity ecdh-sha2-1.3.132.0.36 {
    base key-exchange-alg-base;
    description
      "ECDH-SHA2-1.3.132.0.36 (nistk409, sect409k1)";
    reference
      "RFC 5656:
         Elliptic Curve Algorithm Integration in the
         Secure Shell Transport Layer";
  }

  identity ecdh-sha2-1.3.132.0.37 {
    base key-exchange-alg-base;
    description
      "ECDH-SHA2-1.3.132.0.37 (nistb409, sect409r1)";
    reference
      "RFC 5656:
         Elliptic Curve Algorithm Integration in the
         Secure Shell Transport Layer";
  }

  identity ecdh-sha2-1.3.132.0.38 {
    base key-exchange-alg-base;
    description
      "ECDH-SHA2-1.3.132.0.38 (nistt571, sect571k1)";
    reference
      "RFC 5656:
         Elliptic Curve Algorithm Integration in the
         Secure Shell Transport Layer";
  }

  identity ecmqv-sha2 {
    base key-exchange-alg-base;
    description
      "ECMQV-SHA2";
    reference
      "RFC 5656:
         Elliptic Curve Algorithm Integration in the
         Secure Shell Transport Layer";
  }

  identity gss-group1-sha1-nistp256 {
    base key-exchange-alg-base;
    status deprecated;
    description
      "GSS-GROUP1-SHA1-NISTP256 (secp256r1)";
    reference
      "RFC 8732:
         Generic Security Service Application Program Interface
         (GSS-API) Key Exchange with SHA-2";
  }

  identity gss-group1-sha1-nistp384 {
    base key-exchange-alg-base;
    status deprecated;
    description
      "GSS-GROUP1-SHA1-NISTP384 (secp384r1)";
    reference
      "RFC 8732:
         Generic Security Service Application Program Interface
         (GSS-API) Key Exchange with SHA-2";
  }

  identity gss-group1-sha1-nistp521 {
    base key-exchange-alg-base;
    status deprecated;
    description
      "GSS-GROUP1-SHA1-NISTP521 (secp521r1)";
    reference
      "RFC 8732:
         Generic Security Service Application Program Interface
         (GSS-API) Key Exchange with SHA-2";
  }

  identity gss-group1-sha1-1.3.132.0.1 {
    base key-exchange-alg-base;
    status deprecated;
    description
      "GSS-GROUP1-SHA1-1.3.132.0.1 (nistk163, sect163k1)";
    reference
      "RFC 8732:
         Generic Security Service Application Program Interface
         (GSS-API) Key Exchange with SHA-2";
  }

  identity gss-group1-sha1-1.2.840.10045.3.1.1 {
    base key-exchange-alg-base;
    status deprecated;
    description
      "GSS-GROUP1-SHA1-1.2.840.10045.3.1.1 (nistp192, secp192r1)";
    reference
      "RFC 8732:
         Generic Security Service Application Program Interface
         (GSS-API) Key Exchange with SHA-2";
  }

  identity gss-group1-sha1-1.3.132.0.33 {
    base key-exchange-alg-base;
    status deprecated;
    description
      "GSS-GROUP1-SHA1-1.3.132.0.33 (nistp224, secp224r1)";
    reference
      "RFC 8732:
         Generic Security Service Application Program Interface
         (GSS-API) Key Exchange with SHA-2";
  }

  identity gss-group1-sha1-1.3.132.0.26 {
    base key-exchange-alg-base;
    status deprecated;
    description
      "GSS-GROUP1-SHA1-1.3.132.0.26 (nistk233, sect233k1)";
    reference
      "RFC 8732:
         Generic Security Service Application Program Interface
         (GSS-API) Key Exchange with SHA-2";
  }

  identity gss-group1-sha1-1.3.132.0.27 {
    base key-exchange-alg-base;
    status deprecated;
    description
      "GSS-GROUP1-SHA1-1.3.132.0.27 (nistb233, sect233r1)";
    reference
      "RFC 8732:
         Generic Security Service Application Program Interface
         (GSS-API) Key Exchange with SHA-2";
  }

  identity gss-group1-sha1-1.3.132.0.16 {
    base key-exchange-alg-base;
    status deprecated;
    description
      "GSS-GROUP1-SHA1-1.3.132.0.16 (nistk283, sect283k1)";
    reference
      "RFC 8732:
         Generic Security Service Application Program Interface
         (GSS-API) Key Exchange with SHA-2";
  }

  identity gss-group1-sha1-1.3.132.0.36 {
    base key-exchange-alg-base;
    status deprecated;
    description
      "GSS-GROUP1-SHA1-1.3.132.0.36 (nistk409, sect409k1)";
    reference
      "RFC 8732:
         Generic Security Service Application Program Interface
         (GSS-API) Key Exchange with SHA-2";
  }

  identity gss-group1-sha1-1.3.132.0.37 {
    base key-exchange-alg-base;
    status deprecated;
    description
      "GSS-GROUP1-SHA1-1.3.132.0.37 (nistb409, sect409r1)";
    reference
      "RFC 8732:
         Generic Security Service Application Program Interface
         (GSS-API) Key Exchange with SHA-2";
  }

  identity gss-group1-sha1-1.3.132.0.38 {
    base key-exchange-alg-base;
    status deprecated;
    description
      "GSS-GROUP1-SHA1-1.3.132.0.38 (nistt571, sect571k1)";
    reference
      "RFC 8732:
         Generic Security Service Application Program Interface
         (GSS-API) Key Exchange with SHA-2";
  }

  identity gss-group1-sha1-curve25519-sha256 {
    base key-exchange-alg-base;
    status deprecated;
    description
      "GSS-GROUP1-SHA1-CURVE25519-SHA256";
    reference
      "RFC 8732:
         Generic Security Service Application Program Interface
         (GSS-API) Key Exchange with SHA-2";
  }

  identity gss-group1-sha1-curve448-sha512 {
    base key-exchange-alg-base;
    status deprecated;
    description
      "GSS-GROUP1-SHA1-CURVE448-SHA512";
    reference
      "RFC 8732:
         Generic Security Service Application Program Interface
         (GSS-API) Key Exchange with SHA-2";
  }

  identity gss-group14-sha1-nistp256 {
    base key-exchange-alg-base;
    status deprecated;
    description
      "GSS-GROUP14-SHA1-NISTP256 (secp256r1)";
    reference
      "RFC 8732:
         Generic Security Service Application Program Interface
         (GSS-API) Key Exchange with SHA-2";
  }

  identity gss-group14-sha1-nistp384 {
    base key-exchange-alg-base;
    status deprecated;
    description
      "GSS-GROUP14-SHA1-NISTP384 (secp384r1)";
    reference
      "RFC 8732:
         Generic Security Service Application Program Interface
         (GSS-API) Key Exchange with SHA-2";
  }

  identity gss-group14-sha1-nistp521 {
    base key-exchange-alg-base;
    status deprecated;
    description
      "GSS-GROUP14-SHA1-NISTP521 (secp521r1)";
    reference
      "RFC 8732:
         Generic Security Service Application Program Interface
         (GSS-API) Key Exchange with SHA-2";
  }

  identity gss-group14-sha1-1.3.132.0.1 {
    base key-exchange-alg-base;
    status deprecated;
    description
      "GSS-GROUP14-SHA1-1.3.132.0.1 (nistk163, sect163k1)";
    reference
      "RFC 8732:
         Generic Security Service Application Program Interface
         (GSS-API) Key Exchange with SHA-2";
  }

  identity gss-group14-sha1-1.2.840.10045.3.1.1 {
    base key-exchange-alg-base;
    status deprecated;
    description
      "GSS-GROUP14-SHA1-1.2.840.10045.3.1.1 (nistp192, secp192r1)";
    reference
      "RFC 8732:
         Generic Security Service Application Program Interface
         (GSS-API) Key Exchange with SHA-2";
  }

  identity gss-group14-sha1-1.3.132.0.33 {
    base key-exchange-alg-base;
    status deprecated;
    description
      "GSS-GROUP14-SHA1-1.3.132.0.33 (nistp224, secp224r1)";
    reference
      "RFC 8732:
         Generic Security Service Application Program Interface
         (GSS-API) Key Exchange with SHA-2";
  }

  identity gss-group14-sha1-1.3.132.0.26 {
    base key-exchange-alg-base;
    status deprecated;
    description
      "GSS-GROUP14-SHA1-1.3.132.0.26 (nistk233, sect233k1)";
    reference
      "RFC 8732:
         Generic Security Service Application Program Interface
         (GSS-API) Key Exchange with SHA-2";
  }

  identity gss-group14-sha1-1.3.132.0.27 {
    base key-exchange-alg-base;
    status deprecated;
    description
      "GSS-GROUP14-SHA1-1.3.132.0.27 (nistb233, sect233r1)";
    reference
      "RFC 8732:
         Generic Security Service Application Program Interface
         (GSS-API) Key Exchange with SHA-2";
  }

  identity gss-group14-sha1-1.3.132.0.16 {
    base key-exchange-alg-base;
    status deprecated;
    description
      "GSS-GROUP14-SHA1-1.3.132.0.16 (nistk283, sect283k1)";
    reference
      "RFC 8732:
         Generic Security Service Application Program Interface
         (GSS-API) Key Exchange with SHA-2";
  }

  identity gss-group14-sha1-1.3.132.0.36 {
    base key-exchange-alg-base;
    status deprecated;
    description
      "GSS-GROUP14-SHA1-1.3.132.0.36 (nistk409, sect409k1)";
    reference
      "RFC 8732:
         Generic Security Service Application Program Interface
         (GSS-API) Key Exchange with SHA-2";
  }

  identity gss-group14-sha1-1.3.132.0.37 {
    base key-exchange-alg-base;
    status deprecated;
    description
      "GSS-GROUP14-SHA1-1.3.132.0.37 (nistb409, sect409r1)";
    reference
      "RFC 8732:
         Generic Security Service Application Program Interface
         (GSS-API) Key Exchange with SHA-2";
  }

  identity gss-group14-sha1-1.3.132.0.38 {
    base key-exchange-alg-base;
    status deprecated;
    description
      "GSS-GROUP14-SHA1-1.3.132.0.38 (nistt571, sect571k1)";
    reference
      "RFC 8732:
         Generic Security Service Application Program Interface
         (GSS-API) Key Exchange with SHA-2";
  }

  identity gss-group14-sha1-curve25519-sha256 {
    base key-exchange-alg-base;
    status deprecated;
    description
      "GSS-GROUP14-SHA1-CURVE25519-SHA256";
    reference
      "RFC 8732:
         Generic Security Service Application Program Interface
         (GSS-API) Key Exchange with SHA-2";
  }

  identity gss-group14-sha1-curve448-sha512 {
    base key-exchange-alg-base;
    status deprecated;
    description
      "GSS-GROUP14-SHA1-CURVE448-SHA512";
    reference
      "RFC 8732:
         Generic Security Service Application Program Interface
         (GSS-API) Key Exchange with SHA-2";
  }

  identity gss-gex-sha1-nistp256 {
    base key-exchange-alg-base;
    status deprecated;
    description
      "GSS-GEX-SHA1-NISTP256 (secp256r1)";
    reference
      "RFC 8732:
         Generic Security Service Application Program Interface
         (GSS-API) Key Exchange with SHA-2";
  }

  identity gss-gex-sha1-nistp384 {
    base key-exchange-alg-base;
    status deprecated;
    description
      "GSS-GEX-SHA1-NISTP384 (secp384r1)";
    reference
      "RFC 8732:
         Generic Security Service Application Program Interface
         (GSS-API) Key Exchange with SHA-2";
  }

  identity gss-gex-sha1-nistp521 {
    base key-exchange-alg-base;
    status deprecated;
    description
      "GSS-GEX-SHA1-NISTP521 (secp521r1)";
    reference
      "RFC 8732:
         Generic Security Service Application Program Interface
         (GSS-API) Key Exchange with SHA-2";
  }

  identity gss-gex-sha1-1.3.132.0.1 {
    base key-exchange-alg-base;
    status deprecated;
    description
      "GSS-GEX-SHA1-1.3.132.0.1 (nistk163, sect163k1)";
    reference
      "RFC 8732:
         Generic Security Service Application Program Interface
         (GSS-API) Key Exchange with SHA-2";
  }

  identity gss-gex-sha1-1.2.840.10045.3.1.1 {
    base key-exchange-alg-base;
    status deprecated;
    description
      "GSS-GEX-SHA1-1.2.840.10045.3.1.1 (nistp192, secp192r1)";
    reference
      "RFC 8732:
         Generic Security Service Application Program Interface
         (GSS-API) Key Exchange with SHA-2";
  }

  identity gss-gex-sha1-1.3.132.0.33 {
    base key-exchange-alg-base;
    status deprecated;
    description
      "GSS-GEX-SHA1-1.3.132.0.33 (nistp224, secp224r1)";
    reference
      "RFC 8732:
         Generic Security Service Application Program Interface
         (GSS-API) Key Exchange with SHA-2";
  }

  identity gss-gex-sha1-1.3.132.0.26 {
    base key-exchange-alg-base;
    status deprecated;
    description
      "GSS-GEX-SHA1-1.3.132.0.26 (nistk233, sect233k1)";
    reference
      "RFC 8732:
         Generic Security Service Application Program Interface
         (GSS-API) Key Exchange with SHA-2";
  }

  identity gss-gex-sha1-1.3.132.0.27 {
    base key-exchange-alg-base;
    status deprecated;
    description
      "GSS-GEX-SHA1-1.3.132.0.27 (nistb233, sect233r1)";
    reference
      "RFC 8732:
         Generic Security Service Application Program Interface
         (GSS-API) Key Exchange with SHA-2";
  }

  identity gss-gex-sha1-1.3.132.0.16 {
    base key-exchange-alg-base;
    status deprecated;
    description
      "GSS-GEX-SHA1-1.3.132.0.16 (nistk283, sect283k1)";
    reference
      "RFC 8732:
         Generic Security Service Application Program Interface
         (GSS-API) Key Exchange with SHA-2";
  }

  identity gss-gex-sha1-1.3.132.0.36 {
    base key-exchange-alg-base;
    status deprecated;
    description
      "GSS-GEX-SHA1-1.3.132.0.36 (nistk409, sect409k1)";
    reference
      "RFC 8732:
         Generic Security Service Application Program Interface
         (GSS-API) Key Exchange with SHA-2";
  }

  identity gss-gex-sha1-1.3.132.0.37 {
    base key-exchange-alg-base;
    status deprecated;
    description
      "GSS-GEX-SHA1-1.3.132.0.37 (nistb409, sect409r1)";
    reference
      "RFC 8732:
         Generic Security Service Application Program Interface
         (GSS-API) Key Exchange with SHA-2";
  }

  identity gss-gex-sha1-1.3.132.0.38 {
    base key-exchange-alg-base;
    status deprecated;
    description
      "GSS-GEX-SHA1-1.3.132.0.38 (nistt571, sect571k1)";
    reference
      "RFC 8732:
         Generic Security Service Application Program Interface
         (GSS-API) Key Exchange with SHA-2";
  }

  identity gss-gex-sha1-curve25519-sha256 {
    base key-exchange-alg-base;
    status deprecated;
    description
      "GSS-GEX-SHA1-CURVE25519-SHA256";
    reference
      "RFC 8732:
         Generic Security Service Application Program Interface
         (GSS-API) Key Exchange with SHA-2";
  }

  identity gss-gex-sha1-curve448-sha512 {
    base key-exchange-alg-base;
    status deprecated;
    description
      "GSS-GEX-SHA1-CURVE448-SHA512";
    reference
      "RFC 8732:
         Generic Security Service Application Program Interface
         (GSS-API) Key Exchange with SHA-2";
  }

  identity rsa1024-sha1 {
    base key-exchange-alg-base;
    status obsolete;
    description
      "RSA1024-SHA1";
    reference
      "RFC 4432:
         RSA Key Exchange for the Secure Shell (SSH)
         Transport Layer Protocol";
  }

  identity rsa2048-sha256 {
    base key-exchange-alg-base;
    description
      "RSA2048-SHA256";
    reference
      "RFC 4432:
         RSA Key Exchange for the Secure Shell (SSH)
         Transport Layer Protocol";
  }

  identity ext-info-s {
    base key-exchange-alg-base;
    description
      "EXT-INFO-S";
    reference
      "RFC 8308:
         Extension Negotiation in the Secure Shell (SSH) Protocol";
  }

  identity ext-info-c {
    base key-exchange-alg-base;
    description
      "EXT-INFO-C";
    reference
      "RFC 8308:
         Extension Negotiation in the Secure Shell (SSH) Protocol";
  }

  identity gss-group14-sha256-nistp256 {
    base key-exchange-alg-base;
    description
      "GSS-GROUP14-SHA256-NISTP256 (secp256r1)";
    reference
      "RFC 8732:
         Generic Security Service Application Program Interface
         (GSS-API) Key Exchange with SHA-2";
  }

  identity gss-group14-sha256-nistp384 {
    base key-exchange-alg-base;
    description
      "GSS-GROUP14-SHA256-NISTP384 (secp384r1)";
    reference
      "RFC 8732:
         Generic Security Service Application Program Interface
         (GSS-API) Key Exchange with SHA-2";
  }

  identity gss-group14-sha256-nistp521 {
    base key-exchange-alg-base;
    description
      "GSS-GROUP14-SHA256-NISTP521 (secp521r1)";
    reference
      "RFC 8732:
         Generic Security Service Application Program Interface
         (GSS-API) Key Exchange with SHA-2";
  }

  identity gss-group14-sha256-1.3.132.0.1 {
    base key-exchange-alg-base;
    description
      "GSS-GROUP14-SHA256-1.3.132.0.1 (nistk163, sect163k1)";
    reference
      "RFC 8732:
         Generic Security Service Application Program Interface
         (GSS-API) Key Exchange with SHA-2";
  }

  identity gss-group14-sha256-1.2.840.10045.3.1.1 {
    base key-exchange-alg-base;
    description
      "GSS-GROUP14-SHA256-1.2.840.10045.3.1.1 (nistp192, secp192r1)";
    reference
      "RFC 8732:
         Generic Security Service Application Program Interface
         (GSS-API) Key Exchange with SHA-2";
  }

  identity gss-group14-sha256-1.3.132.0.33 {
    base key-exchange-alg-base;
    description
      "GSS-GROUP14-SHA256-1.3.132.0.33 (nistp224, secp224r1)";
    reference
      "RFC 8732:
         Generic Security Service Application Program Interface
         (GSS-API) Key Exchange with SHA-2";
  }

  identity gss-group14-sha256-1.3.132.0.26 {
    base key-exchange-alg-base;
    description
      "GSS-GROUP14-SHA256-1.3.132.0.26 (nistk233, sect233k1)";
    reference
      "RFC 8732:
         Generic Security Service Application Program Interface
         (GSS-API) Key Exchange with SHA-2";
  }

  identity gss-group14-sha256-1.3.132.0.27 {
    base key-exchange-alg-base;
    description
      "GSS-GROUP14-SHA256-1.3.132.0.27 (nistb233, sect233r1)";
    reference
      "RFC 8732:
         Generic Security Service Application Program Interface
         (GSS-API) Key Exchange with SHA-2";
  }

  identity gss-group14-sha256-1.3.132.0.16 {
    base key-exchange-alg-base;
    description
      "GSS-GROUP14-SHA256-1.3.132.0.16 (nistk283, sect283k1)";
    reference
      "RFC 8732:
         Generic Security Service Application Program Interface
         (GSS-API) Key Exchange with SHA-2";
  }

  identity gss-group14-sha256-1.3.132.0.36 {
    base key-exchange-alg-base;
    description
      "GSS-GROUP14-SHA256-1.3.132.0.36 (nistk409, sect409k1)";
    reference
      "RFC 8732:
         Generic Security Service Application Program Interface
         (GSS-API) Key Exchange with SHA-2";
  }

  identity gss-group14-sha256-1.3.132.0.37 {
    base key-exchange-alg-base;
    description
      "GSS-GROUP14-SHA256-1.3.132.0.37 (nistb409, sect409r1)";
    reference
      "RFC 8732:
         Generic Security Service Application Program Interface
         (GSS-API) Key Exchange with SHA-2";
  }

  identity gss-group14-sha256-1.3.132.0.38 {
    base key-exchange-alg-base;
    description
      "GSS-GROUP14-SHA256-1.3.132.0.38 (nistt571, sect571k1)";
    reference
      "RFC 8732:
         Generic Security Service Application Program Interface
         (GSS-API) Key Exchange with SHA-2";
  }

  identity gss-group14-sha256-curve25519-sha256 {
    base key-exchange-alg-base;
    description
      "GSS-GROUP14-SHA256-CURVE25519-SHA256";
    reference
      "RFC 8732:
         Generic Security Service Application Program Interface
         (GSS-API) Key Exchange with SHA-2";
  }

  identity gss-group14-sha256-curve448-sha512 {
    base key-exchange-alg-base;
    description
      "GSS-GROUP14-SHA256-CURVE448-SHA512";
    reference
      "RFC 8732:
         Generic Security Service Application Program Interface
         (GSS-API) Key Exchange with SHA-2";
  }

  identity gss-group15-sha512-nistp256 {
    base key-exchange-alg-base;
    description
      "GSS-GROUP15-SHA512-NISTP256 (secp256r1)";
    reference
      "RFC 8732:
         Generic Security Service Application Program Interface
         (GSS-API) Key Exchange with SHA-2";
  }

  identity gss-group15-sha512-nistp384 {
    base key-exchange-alg-base;
    description
      "GSS-GROUP15-SHA512-NISTP384 (secp384r1)";
    reference
      "RFC 8732:
         Generic Security Service Application Program Interface
         (GSS-API) Key Exchange with SHA-2";
  }

  identity gss-group15-sha512-nistp521 {
    base key-exchange-alg-base;
    description
      "GSS-GROUP15-SHA512-NISTP521 (secp521r1)";
    reference
      "RFC 8732:
         Generic Security Service Application Program Interface
         (GSS-API) Key Exchange with SHA-2";
  }

  identity gss-group15-sha512-1.3.132.0.1 {
    base key-exchange-alg-base;
    description
      "GSS-GROUP15-SHA512-1.3.132.0.1 (nistk163, sect163k1)";
    reference
      "RFC 8732:
         Generic Security Service Application Program Interface
         (GSS-API) Key Exchange with SHA-2";
  }

  identity gss-group15-sha512-1.2.840.10045.3.1.1 {
    base key-exchange-alg-base;
    description
      "GSS-GROUP15-SHA512-1.2.840.10045.3.1.1 (nistp192, secp192r1)";
    reference
      "RFC 8732:
         Generic Security Service Application Program Interface
         (GSS-API) Key Exchange with SHA-2";
  }

  identity gss-group15-sha512-1.3.132.0.33 {
    base key-exchange-alg-base;
    description
      "GSS-GROUP15-SHA512-1.3.132.0.33 (nistp224, secp224r1)";
    reference
      "RFC 8732:
         Generic Security Service Application Program Interface
         (GSS-API) Key Exchange with SHA-2";
  }

  identity gss-group15-sha512-1.3.132.0.26 {
    base key-exchange-alg-base;
    description
      "GSS-GROUP15-SHA512-1.3.132.0.26 (nistk233, sect233k1)";
    reference
      "RFC 8732:
         Generic Security Service Application Program Interface
         (GSS-API) Key Exchange with SHA-2";
  }

  identity gss-group15-sha512-1.3.132.0.27 {
    base key-exchange-alg-base;
    description
      "GSS-GROUP15-SHA512-1.3.132.0.27 (nistb233, sect233r1)";
    reference
      "RFC 8732:
         Generic Security Service Application Program Interface
         (GSS-API) Key Exchange with SHA-2";
  }

  identity gss-group15-sha512-1.3.132.0.16 {
    base key-exchange-alg-base;
    description
      "GSS-GROUP15-SHA512-1.3.132.0.16 (nistk283, sect283k1)";
    reference
      "RFC 8732:
         Generic Security Service Application Program Interface
         (GSS-API) Key Exchange with SHA-2";
  }

  identity gss-group15-sha512-1.3.132.0.36 {
    base key-exchange-alg-base;
    description
      "GSS-GROUP15-SHA512-1.3.132.0.36 (nistk409, sect409k1)";
    reference
      "RFC 8732:
         Generic Security Service Application Program Interface
         (GSS-API) Key Exchange with SHA-2";
  }

  identity gss-group15-sha512-1.3.132.0.37 {
    base key-exchange-alg-base;
    description
      "GSS-GROUP15-SHA512-1.3.132.0.37 (nistb409, sect409r1)";
    reference
      "RFC 8732:
         Generic Security Service Application Program Interface
         (GSS-API) Key Exchange with SHA-2";
  }

  identity gss-group15-sha512-1.3.132.0.38 {
    base key-exchange-alg-base;
    description
      "GSS-GROUP15-SHA512-1.3.132.0.38 (nistt571, sect571k1)";
    reference
      "RFC 8732:
         Generic Security Service Application Program Interface
         (GSS-API) Key Exchange with SHA-2";
  }

  identity gss-group15-sha512-curve25519-sha256 {
    base key-exchange-alg-base;
    description
      "GSS-GROUP15-SHA512-CURVE25519-SHA256";
    reference
      "RFC 8732:
         Generic Security Service Application Program Interface
         (GSS-API) Key Exchange with SHA-2";
  }

  identity gss-group15-sha512-curve448-sha512 {
    base key-exchange-alg-base;
    description
      "GSS-GROUP15-SHA512-CURVE448-SHA512";
    reference
      "RFC 8732:
         Generic Security Service Application Program Interface
         (GSS-API) Key Exchange with SHA-2";
  }

  identity gss-group16-sha512-nistp256 {
    base key-exchange-alg-base;
    description
      "GSS-GROUP16-SHA512-NISTP256 (secp256r1)";
    reference
      "RFC 8732:
         Generic Security Service Application Program Interface
         (GSS-API) Key Exchange with SHA-2";
  }

  identity gss-group16-sha512-nistp384 {
    base key-exchange-alg-base;
    description
      "GSS-GROUP16-SHA512-NISTP384 (secp384r1)";
    reference
      "RFC 8732:
         Generic Security Service Application Program Interface
         (GSS-API) Key Exchange with SHA-2";
  }

  identity gss-group16-sha512-nistp521 {
    base key-exchange-alg-base;
    description
      "GSS-GROUP16-SHA512-NISTP521 (secp521r1)";
    reference
      "RFC 8732:
         Generic Security Service Application Program Interface
         (GSS-API) Key Exchange with SHA-2";
  }

  identity gss-group16-sha512-1.3.132.0.1 {
    base key-exchange-alg-base;
    description
      "GSS-GROUP16-SHA512-1.3.132.0.1 (nistk163, sect163k1)";
    reference
      "RFC 8732:
         Generic Security Service Application Program Interface
         (GSS-API) Key Exchange with SHA-2";
  }

  identity gss-group16-sha512-1.2.840.10045.3.1.1 {
    base key-exchange-alg-base;
    description
      "GSS-GROUP16-SHA512-1.2.840.10045.3.1.1 (nistp192, secp192r1)";
    reference
      "RFC 8732:
         Generic Security Service Application Program Interface
         (GSS-API) Key Exchange with SHA-2";
  }

  identity gss-group16-sha512-1.3.132.0.33 {
    base key-exchange-alg-base;
    description
      "GSS-GROUP16-SHA512-1.3.132.0.33 (nistp224, secp224r1)";
    reference
      "RFC 8732:
         Generic Security Service Application Program Interface
         (GSS-API) Key Exchange with SHA-2";
  }

  identity gss-group16-sha512-1.3.132.0.26 {
    base key-exchange-alg-base;
    description
      "GSS-GROUP16-SHA512-1.3.132.0.26 (nistk233, sect233k1)";
    reference
      "RFC 8732:
         Generic Security Service Application Program Interface
         (GSS-API) Key Exchange with SHA-2";
  }

  identity gss-group16-sha512-1.3.132.0.27 {
    base key-exchange-alg-base;
    description
      "GSS-GROUP16-SHA512-1.3.132.0.27 (nistb233, sect233r1)";
    reference
      "RFC 8732:
         Generic Security Service Application Program Interface
         (GSS-API) Key Exchange with SHA-2";
  }

  identity gss-group16-sha512-1.3.132.0.16 {
    base key-exchange-alg-base;
    description
      "GSS-GROUP16-SHA512-1.3.132.0.16 (nistk283, sect283k1)";
    reference
      "RFC 8732:
         Generic Security Service Application Program Interface
         (GSS-API) Key Exchange with SHA-2";
  }

  identity gss-group16-sha512-1.3.132.0.36 {
    base key-exchange-alg-base;
    description
      "GSS-GROUP16-SHA512-1.3.132.0.36 (nistk409, sect409k1)";
    reference
      "RFC 8732:
         Generic Security Service Application Program Interface
         (GSS-API) Key Exchange with SHA-2";
  }

  identity gss-group16-sha512-1.3.132.0.37 {
    base key-exchange-alg-base;
    description
      "GSS-GROUP16-SHA512-1.3.132.0.37 (nistb409, sect409r1)";
    reference
      "RFC 8732:
         Generic Security Service Application Program Interface
         (GSS-API) Key Exchange with SHA-2";
  }

  identity gss-group16-sha512-1.3.132.0.38 {
    base key-exchange-alg-base;
    description
      "GSS-GROUP16-SHA512-1.3.132.0.38 (nistt571, sect571k1)";
    reference
      "RFC 8732:
         Generic Security Service Application Program Interface
         (GSS-API) Key Exchange with SHA-2";
  }

  identity gss-group16-sha512-curve25519-sha256 {
    base key-exchange-alg-base;
    description
      "GSS-GROUP16-SHA512-CURVE25519-SHA256";
    reference
      "RFC 8732:
         Generic Security Service Application Program Interface
         (GSS-API) Key Exchange with SHA-2";
  }

  identity gss-group16-sha512-curve448-sha512 {
    base key-exchange-alg-base;
    description
      "GSS-GROUP16-SHA512-CURVE448-SHA512";
    reference
      "RFC 8732:
         Generic Security Service Application Program Interface
         (GSS-API) Key Exchange with SHA-2";
  }

  identity gss-group17-sha512-nistp256 {
    base key-exchange-alg-base;
    description
      "GSS-GROUP17-SHA512-NISTP256 (secp256r1)";
    reference
      "RFC 8732:
         Generic Security Service Application Program Interface
         (GSS-API) Key Exchange with SHA-2";
  }

  identity gss-group17-sha512-nistp384 {
    base key-exchange-alg-base;
    description
      "GSS-GROUP17-SHA512-NISTP384 (secp384r1)";
    reference
      "RFC 8732:
         Generic Security Service Application Program Interface
         (GSS-API) Key Exchange with SHA-2";
  }

  identity gss-group17-sha512-nistp521 {
    base key-exchange-alg-base;
    description
      "GSS-GROUP17-SHA512-NISTP521 (secp521r1)";
    reference
      "RFC 8732:
         Generic Security Service Application Program Interface
         (GSS-API) Key Exchange with SHA-2";
  }

  identity gss-group17-sha512-1.3.132.0.1 {
    base key-exchange-alg-base;
    description
      "GSS-GROUP17-SHA512-1.3.132.0.1 (nistk163, sect163k1)";
    reference
      "RFC 8732:
         Generic Security Service Application Program Interface
         (GSS-API) Key Exchange with SHA-2";
  }

  identity gss-group17-sha512-1.2.840.10045.3.1.1 {
    base key-exchange-alg-base;
    description
      "GSS-GROUP17-SHA512-1.2.840.10045.3.1.1 (nistp192, secp192r1)";
    reference
      "RFC 8732:
         Generic Security Service Application Program Interface
         (GSS-API) Key Exchange with SHA-2";
  }

  identity gss-group17-sha512-1.3.132.0.33 {
    base key-exchange-alg-base;
    description
      "GSS-GROUP17-SHA512-1.3.132.0.33 (nistp224, secp224r1)";
    reference
      "RFC 8732:
         Generic Security Service Application Program Interface
         (GSS-API) Key Exchange with SHA-2";
  }

  identity gss-group17-sha512-1.3.132.0.26 {
    base key-exchange-alg-base;
    description
      "GSS-GROUP17-SHA512-1.3.132.0.26 (nistk233, sect233k1)";
    reference
      "RFC 8732:
         Generic Security Service Application Program Interface
         (GSS-API) Key Exchange with SHA-2";
  }

  identity gss-group17-sha512-1.3.132.0.27 {
    base key-exchange-alg-base;
    description
      "GSS-GROUP17-SHA512-1.3.132.0.27 (nistb233, sect233r1)";
    reference
      "RFC 8732:
         Generic Security Service Application Program Interface
         (GSS-API) Key Exchange with SHA-2";
  }

  identity gss-group17-sha512-1.3.132.0.16 {
    base key-exchange-alg-base;
    description
      "GSS-GROUP17-SHA512-1.3.132.0.16 (nistk283, sect283k1)";
    reference
      "RFC 8732:
         Generic Security Service Application Program Interface
         (GSS-API) Key Exchange with SHA-2";
  }

  identity gss-group17-sha512-1.3.132.0.36 {
    base key-exchange-alg-base;
    description
      "GSS-GROUP17-SHA512-1.3.132.0.36 (nistk409, sect409k1)";
    reference
      "RFC 8732:
         Generic Security Service Application Program Interface
         (GSS-API) Key Exchange with SHA-2";
  }

  identity gss-group17-sha512-1.3.132.0.37 {
    base key-exchange-alg-base;
    description
      "GSS-GROUP17-SHA512-1.3.132.0.37 (nistb409, sect409r1)";
    reference
      "RFC 8732:
         Generic Security Service Application Program Interface
         (GSS-API) Key Exchange with SHA-2";
  }

  identity gss-group17-sha512-1.3.132.0.38 {
    base key-exchange-alg-base;
    description
      "GSS-GROUP17-SHA512-1.3.132.0.38 (nistt571, sect571k1)";
    reference
      "RFC 8732:
         Generic Security Service Application Program Interface
         (GSS-API) Key Exchange with SHA-2";
  }

  identity gss-group17-sha512-curve25519-sha256 {
    base key-exchange-alg-base;
    description
      "GSS-GROUP17-SHA512-CURVE25519-SHA256";
    reference
      "RFC 8732:
         Generic Security Service Application Program Interface
         (GSS-API) Key Exchange with SHA-2";
  }

  identity gss-group17-sha512-curve448-sha512 {
    base key-exchange-alg-base;
    description
      "GSS-GROUP17-SHA512-CURVE448-SHA512";
    reference
      "RFC 8732:
         Generic Security Service Application Program Interface
         (GSS-API) Key Exchange with SHA-2";
  }

  identity gss-group18-sha512-nistp256 {
    base key-exchange-alg-base;
    description
      "GSS-GROUP18-SHA512-NISTP256 (secp256r1)";
    reference
      "RFC 8732:
         Generic Security Service Application Program Interface
         (GSS-API) Key Exchange with SHA-2";
  }

  identity gss-group18-sha512-nistp384 {
    base key-exchange-alg-base;
    description
      "GSS-GROUP18-SHA512-NISTP384 (secp384r1)";
    reference
      "RFC 8732:
         Generic Security Service Application Program Interface
         (GSS-API) Key Exchange with SHA-2";
  }

  identity gss-group18-sha512-nistp521 {
    base key-exchange-alg-base;
    description
      "GSS-GROUP18-SHA512-NISTP521 (secp521r1)";
    reference
      "RFC 8732:
         Generic Security Service Application Program Interface
         (GSS-API) Key Exchange with SHA-2";
  }

  identity gss-group18-sha512-1.3.132.0.1 {
    base key-exchange-alg-base;
    description
      "GSS-GROUP18-SHA512-1.3.132.0.1 (nistk163, sect163k1)";
    reference
      "RFC 8732:
         Generic Security Service Application Program Interface
         (GSS-API) Key Exchange with SHA-2";
  }

  identity gss-group18-sha512-1.2.840.10045.3.1.1 {
    base key-exchange-alg-base;
    description
      "GSS-GROUP18-SHA512-1.2.840.10045.3.1.1 (nistp192, secp192r1)";
    reference
      "RFC 8732:
         Generic Security Service Application Program Interface
         (GSS-API) Key Exchange with SHA-2";
  }

  identity gss-group18-sha512-1.3.132.0.33 {
    base key-exchange-alg-base;
    description
      "GSS-GROUP18-SHA512-1.3.132.0.33 (nistp224, secp224r1)";
    reference
      "RFC 8732:
         Generic Security Service Application Program Interface
         (GSS-API) Key Exchange with SHA-2";
  }

  identity gss-group18-sha512-1.3.132.0.26 {
    base key-exchange-alg-base;
    description
      "GSS-GROUP18-SHA512-1.3.132.0.26 (nistk233, sect233k1)";
    reference
      "RFC 8732:
         Generic Security Service Application Program Interface
         (GSS-API) Key Exchange with SHA-2";
  }

  identity gss-group18-sha512-1.3.132.0.27 {
    base key-exchange-alg-base;
    description
      "GSS-GROUP18-SHA512-1.3.132.0.27 (nistb233, sect233r1)";
    reference
      "RFC 8732:
         Generic Security Service Application Program Interface
         (GSS-API) Key Exchange with SHA-2";
  }

  identity gss-group18-sha512-1.3.132.0.16 {
    base key-exchange-alg-base;
    description
      "GSS-GROUP18-SHA512-1.3.132.0.16 (nistk283, sect283k1)";
    reference
      "RFC 8732:
         Generic Security Service Application Program Interface
         (GSS-API) Key Exchange with SHA-2";
  }

  identity gss-group18-sha512-1.3.132.0.36 {
    base key-exchange-alg-base;
    description
      "GSS-GROUP18-SHA512-1.3.132.0.36 (nistk409, sect409k1)";
    reference
      "RFC 8732:
         Generic Security Service Application Program Interface
         (GSS-API) Key Exchange with SHA-2";
  }

  identity gss-group18-sha512-1.3.132.0.37 {
    base key-exchange-alg-base;
    description
      "GSS-GROUP18-SHA512-1.3.132.0.37 (nistb409, sect409r1)";
    reference
      "RFC 8732:
         Generic Security Service Application Program Interface
         (GSS-API) Key Exchange with SHA-2";
  }

  identity gss-group18-sha512-1.3.132.0.38 {
    base key-exchange-alg-base;
    description
      "GSS-GROUP18-SHA512-1.3.132.0.38 (nistt571, sect571k1)";
    reference
      "RFC 8732:
         Generic Security Service Application Program Interface
         (GSS-API) Key Exchange with SHA-2";
  }

  identity gss-group18-sha512-curve25519-sha256 {
    base key-exchange-alg-base;
    description
      "GSS-GROUP18-SHA512-CURVE25519-SHA256";
    reference
      "RFC 8732:
         Generic Security Service Application Program Interface
         (GSS-API) Key Exchange with SHA-2";
  }

  identity gss-group18-sha512-curve448-sha512 {
    base key-exchange-alg-base;
    description
      "GSS-GROUP18-SHA512-CURVE448-SHA512";
    reference
      "RFC 8732:
         Generic Security Service Application Program Interface
         (GSS-API) Key Exchange with SHA-2";
  }

  identity gss-nistp256-sha256-nistp256 {
    base key-exchange-alg-base;
    description
      "GSS-NISTP256-SHA256-NISTP256 (secp256r1)";
    reference
      "RFC 8732:
         Generic Security Service Application Program Interface
         (GSS-API) Key Exchange with SHA-2";
  }

  identity gss-nistp256-sha256-nistp384 {
    base key-exchange-alg-base;
    description
      "GSS-NISTP256-SHA256-NISTP384 (secp384r1)";
    reference
      "RFC 8732:
         Generic Security Service Application Program Interface
         (GSS-API) Key Exchange with SHA-2";
  }

  identity gss-nistp256-sha256-nistp521 {
    base key-exchange-alg-base;
    description
      "GSS-NISTP256-SHA256-NISTP521 (secp521r1)";
    reference
      "RFC 8732:
         Generic Security Service Application Program Interface
         (GSS-API) Key Exchange with SHA-2";
  }

  identity gss-nistp256-sha256-1.3.132.0.1 {
    base key-exchange-alg-base;
    description
      "GSS-NISTP256-SHA256-1.3.132.0.1 (nistk163, sect163k1)";
    reference
      "RFC 8732:
         Generic Security Service Application Program Interface
         (GSS-API) Key Exchange with SHA-2";
  }

  identity gss-nistp256-sha256-1.2.840.10045.3.1.1 {
    base key-exchange-alg-base;
    description
      "GSS-NISTP256-SHA256-1.2.840.10045.3.1.1 (nistp192, secp192r1)";
    reference
      "RFC 8732:
         Generic Security Service Application Program Interface
         (GSS-API) Key Exchange with SHA-2";
  }

  identity gss-nistp256-sha256-1.3.132.0.33 {
    base key-exchange-alg-base;
    description
      "GSS-NISTP256-SHA256-1.3.132.0.33 (nistp224, secp224r1)";
    reference
      "RFC 8732:
         Generic Security Service Application Program Interface
         (GSS-API) Key Exchange with SHA-2";
  }

  identity gss-nistp256-sha256-1.3.132.0.26 {
    base key-exchange-alg-base;
    description
      "GSS-NISTP256-SHA256-1.3.132.0.26 (nistk233, sect233k1)";
    reference
      "RFC 8732:
         Generic Security Service Application Program Interface
         (GSS-API) Key Exchange with SHA-2";
  }

  identity gss-nistp256-sha256-1.3.132.0.27 {
    base key-exchange-alg-base;
    description
      "GSS-NISTP256-SHA256-1.3.132.0.27 (nistb233, sect233r1)";
    reference
      "RFC 8732:
         Generic Security Service Application Program Interface
         (GSS-API) Key Exchange with SHA-2";
  }

  identity gss-nistp256-sha256-1.3.132.0.16 {
    base key-exchange-alg-base;
    description
      "GSS-NISTP256-SHA256-1.3.132.0.16 (nistk283, sect283k1)";
    reference
      "RFC 8732:
         Generic Security Service Application Program Interface
         (GSS-API) Key Exchange with SHA-2";
  }

  identity gss-nistp256-sha256-1.3.132.0.36 {
    base key-exchange-alg-base;
    description
      "GSS-NISTP256-SHA256-1.3.132.0.36 (nistk409, sect409k1)";
    reference
      "RFC 8732:
         Generic Security Service Application Program Interface
         (GSS-API) Key Exchange with SHA-2";
  }

  identity gss-nistp256-sha256-1.3.132.0.37 {
    base key-exchange-alg-base;
    description
      "GSS-NISTP256-SHA256-1.3.132.0.37 (nistb409, sect409r1)";
    reference
      "RFC 8732:
         Generic Security Service Application Program Interface
         (GSS-API) Key Exchange with SHA-2";
  }

  identity gss-nistp256-sha256-1.3.132.0.38 {
    base key-exchange-alg-base;
    description
      "GSS-NISTP256-SHA256-1.3.132.0.38 (nistt571, sect571k1)";
    reference
      "RFC 8732:
         Generic Security Service Application Program Interface
         (GSS-API) Key Exchange with SHA-2";
  }

  identity gss-nistp256-sha256-curve25519-sha256 {
    base key-exchange-alg-base;
    description
      "GSS-NISTP256-SHA256-CURVE25519-SHA256";
    reference
      "RFC 8732:
         Generic Security Service Application Program Interface
         (GSS-API) Key Exchange with SHA-2";
  }

  identity gss-nistp256-sha256-curve448-sha512 {
    base key-exchange-alg-base;
    description
      "GSS-NISTP256-SHA256-CURVE448-SHA512";
    reference
      "RFC 8732:
         Generic Security Service Application Program Interface
         (GSS-API) Key Exchange with SHA-2";
  }

  identity gss-nistp384-sha384-nistp256 {
    base key-exchange-alg-base;
    description
      "GSS-NISTP384-SHA384-NISTP256 (secp256r1)";
    reference
      "RFC 8732:
         Generic Security Service Application Program Interface
         (GSS-API) Key Exchange with SHA-2";
  }

  identity gss-nistp384-sha384-nistp384 {
    base key-exchange-alg-base;
    description
      "GSS-NISTP384-SHA384-NISTP384 (secp384r1)";
    reference
      "RFC 8732:
         Generic Security Service Application Program Interface
         (GSS-API) Key Exchange with SHA-2";
  }

  identity gss-nistp384-sha384-nistp521 {
    base key-exchange-alg-base;
    description
      "GSS-NISTP384-SHA384-NISTP521 (secp521r1)";
    reference
      "RFC 8732:
         Generic Security Service Application Program Interface
         (GSS-API) Key Exchange with SHA-2";
  }

  identity gss-nistp384-sha384-1.3.132.0.1 {
    base key-exchange-alg-base;
    description
      "GSS-NISTP384-SHA384-1.3.132.0.1 (nistk163, sect163k1)";
    reference
      "RFC 8732:
         Generic Security Service Application Program Interface
         (GSS-API) Key Exchange with SHA-2";
  }

  identity gss-nistp384-sha384-1.2.840.10045.3.1.1 {
    base key-exchange-alg-base;
    description
      "GSS-NISTP384-SHA384-1.2.840.10045.3.1.1 (nistp192, secp192r1)";
    reference
      "RFC 8732:
         Generic Security Service Application Program Interface
         (GSS-API) Key Exchange with SHA-2";
  }

  identity gss-nistp384-sha384-1.3.132.0.33 {
    base key-exchange-alg-base;
    description
      "GSS-NISTP384-SHA384-1.3.132.0.33 (nistp224, secp224r1)";
    reference
      "RFC 8732:
         Generic Security Service Application Program Interface
         (GSS-API) Key Exchange with SHA-2";
  }

  identity gss-nistp384-sha384-1.3.132.0.26 {
    base key-exchange-alg-base;
    description
      "GSS-NISTP384-SHA384-1.3.132.0.26 (nistk233, sect233k1)";
    reference
      "RFC 8732:
         Generic Security Service Application Program Interface
         (GSS-API) Key Exchange with SHA-2";
  }

  identity gss-nistp384-sha384-1.3.132.0.27 {
    base key-exchange-alg-base;
    description
      "GSS-NISTP384-SHA384-1.3.132.0.27 (nistb233, sect233r1)";
    reference
      "RFC 8732:
         Generic Security Service Application Program Interface
         (GSS-API) Key Exchange with SHA-2";
  }

  identity gss-nistp384-sha384-1.3.132.0.16 {
    base key-exchange-alg-base;
    description
      "GSS-NISTP384-SHA384-1.3.132.0.16 (nistk283, sect283k1)";
    reference
      "RFC 8732:
         Generic Security Service Application Program Interface
         (GSS-API) Key Exchange with SHA-2";
  }

  identity gss-nistp384-sha384-1.3.132.0.36 {
    base key-exchange-alg-base;
    description
      "GSS-NISTP384-SHA384-1.3.132.0.36 (nistk409, sect409k1)";
    reference
      "RFC 8732:
         Generic Security Service Application Program Interface
         (GSS-API) Key Exchange with SHA-2";
  }

  identity gss-nistp384-sha384-1.3.132.0.37 {
    base key-exchange-alg-base;
    description
      "GSS-NISTP384-SHA384-1.3.132.0.37 (nistb409, sect409r1)";
    reference
      "RFC 8732:
         Generic Security Service Application Program Interface
         (GSS-API) Key Exchange with SHA-2";
  }

  identity gss-nistp384-sha384-1.3.132.0.38 {
    base key-exchange-alg-base;
    description
      "GSS-NISTP384-SHA384-1.3.132.0.38 (nistt571, sect571k1)";
    reference
      "RFC 8732:
         Generic Security Service Application Program Interface
         (GSS-API) Key Exchange with SHA-2";
  }

  identity gss-nistp384-sha384-curve25519-sha256 {
    base key-exchange-alg-base;
    description
      "GSS-NISTP384-SHA384-CURVE25519-SHA256";
    reference
      "RFC 8732:
         Generic Security Service Application Program Interface
         (GSS-API) Key Exchange with SHA-2";
  }

  identity gss-nistp384-sha384-curve448-sha512 {
    base key-exchange-alg-base;
    description
      "GSS-NISTP384-SHA384-CURVE448-SHA512";
    reference
      "RFC 8732:
         Generic Security Service Application Program Interface
         (GSS-API) Key Exchange with SHA-2";
  }

  identity gss-nistp521-sha512-nistp256 {
    base key-exchange-alg-base;
    description
      "GSS-NISTP521-SHA512-NISTP256 (secp256r1)";
    reference
      "RFC 8732:
         Generic Security Service Application Program Interface
         (GSS-API) Key Exchange with SHA-2";
  }

  identity gss-nistp521-sha512-nistp384 {
    base key-exchange-alg-base;
    description
      "GSS-NISTP521-SHA512-NISTP384 (secp384r1)";
    reference
      "RFC 8732:
         Generic Security Service Application Program Interface
         (GSS-API) Key Exchange with SHA-2";
  }

  identity gss-nistp521-sha512-nistp521 {
    base key-exchange-alg-base;
    description
      "GSS-NISTP521-SHA512-NISTP521 (secp521r1)";
    reference
      "RFC 8732:
         Generic Security Service Application Program Interface
         (GSS-API) Key Exchange with SHA-2";
  }

  identity gss-nistp521-sha512-1.3.132.0.1 {
    base key-exchange-alg-base;
    description
      "GSS-NISTP521-SHA512-1.3.132.0.1 (nistk163, sect163k1)";
    reference
      "RFC 8732:
         Generic Security Service Application Program Interface
         (GSS-API) Key Exchange with SHA-2";
  }

  identity gss-nistp521-sha512-1.2.840.10045.3.1.1 {
    base key-exchange-alg-base;
    description
      "GSS-NISTP521-SHA512-1.2.840.10045.3.1.1 (nistp192, secp192r1)";
    reference
      "RFC 8732:
         Generic Security Service Application Program Interface
         (GSS-API) Key Exchange with SHA-2";
  }

  identity gss-nistp521-sha512-1.3.132.0.33 {
    base key-exchange-alg-base;
    description
      "GSS-NISTP521-SHA512-1.3.132.0.33 (nistp224, secp224r1)";
    reference
      "RFC 8732:
         Generic Security Service Application Program Interface
         (GSS-API) Key Exchange with SHA-2";
  }

  identity gss-nistp521-sha512-1.3.132.0.26 {
    base key-exchange-alg-base;
    description
      "GSS-NISTP521-SHA512-1.3.132.0.26 (nistk233, sect233k1)";
    reference
      "RFC 8732:
         Generic Security Service Application Program Interface
         (GSS-API) Key Exchange with SHA-2";
  }

  identity gss-nistp521-sha512-1.3.132.0.27 {
    base key-exchange-alg-base;
    description
      "GSS-NISTP521-SHA512-1.3.132.0.27 (nistb233, sect233r1)";
    reference
      "RFC 8732:
         Generic Security Service Application Program Interface
         (GSS-API) Key Exchange with SHA-2";
  }

  identity gss-nistp521-sha512-1.3.132.0.16 {
    base key-exchange-alg-base;
    description
      "GSS-NISTP521-SHA512-1.3.132.0.16 (nistk283, sect283k1)";
    reference
      "RFC 8732:
         Generic Security Service Application Program Interface
         (GSS-API) Key Exchange with SHA-2";
  }

  identity gss-nistp521-sha512-1.3.132.0.36 {
    base key-exchange-alg-base;
    description
      "GSS-NISTP521-SHA512-1.3.132.0.36 (nistk409, sect409k1)";
    reference
      "RFC 8732:
         Generic Security Service Application Program Interface
         (GSS-API) Key Exchange with SHA-2";
  }

  identity gss-nistp521-sha512-1.3.132.0.37 {
    base key-exchange-alg-base;
    description
      "GSS-NISTP521-SHA512-1.3.132.0.37 (nistb409, sect409r1)";
    reference
      "RFC 8732:
         Generic Security Service Application Program Interface
         (GSS-API) Key Exchange with SHA-2";
  }

  identity gss-nistp521-sha512-1.3.132.0.38 {
    base key-exchange-alg-base;
    description
      "GSS-NISTP521-SHA512-1.3.132.0.38 (nistt571, sect571k1)";
    reference
      "RFC 8732:
         Generic Security Service Application Program Interface
         (GSS-API) Key Exchange with SHA-2";
  }

  identity gss-nistp521-sha512-curve25519-sha256 {
    base key-exchange-alg-base;
    description
      "GSS-NISTP521-SHA512-CURVE25519-SHA256";
    reference
      "RFC 8732:
         Generic Security Service Application Program Interface
         (GSS-API) Key Exchange with SHA-2";
  }

  identity gss-nistp521-sha512-curve448-sha512 {
    base key-exchange-alg-base;
    description
      "GSS-NISTP521-SHA512-CURVE448-SHA512";
    reference
      "RFC 8732:
         Generic Security Service Application Program Interface
         (GSS-API) Key Exchange with SHA-2";
  }

  identity gss-curve25519-sha256-nistp256 {
    base key-exchange-alg-base;
    description
      "GSS-CURVE25519-SHA256-NISTP256 (secp256r1)";
    reference
      "RFC 8732:
         Generic Security Service Application Program Interface
         (GSS-API) Key Exchange with SHA-2";
  }

  identity gss-curve25519-sha256-nistp384 {
    base key-exchange-alg-base;
    description
      "GSS-CURVE25519-SHA256-NISTP384 (secp384r1)";
    reference
      "RFC 8732:
         Generic Security Service Application Program Interface
         (GSS-API) Key Exchange with SHA-2";
  }

  identity gss-curve25519-sha256-nistp521 {
    base key-exchange-alg-base;
    description
      "GSS-CURVE25519-SHA256-NISTP521 (secp521r1)";
    reference
      "RFC 8732:
         Generic Security Service Application Program Interface
         (GSS-API) Key Exchange with SHA-2";
  }

  identity gss-curve25519-sha256-1.3.132.0.1 {
    base key-exchange-alg-base;
    description
      "GSS-CURVE25519-SHA256-1.3.132.0.1 (nistk163, sect163k1)";
    reference
      "RFC 8732:
         Generic Security Service Application Program Interface
         (GSS-API) Key Exchange with SHA-2";
  }

  identity gss-curve25519-sha256-1.2.840.10045.3.1.1 {
    base key-exchange-alg-base;
    description
      "GSS-CURVE25519-SHA256-1.2.840.10045.3.1.1 (nistp192,
       secp192r1)";
    reference
      "RFC 8732:
         Generic Security Service Application Program Interface
         (GSS-API) Key Exchange with SHA-2";
  }

  identity gss-curve25519-sha256-1.3.132.0.33 {
    base key-exchange-alg-base;
    description
      "GSS-CURVE25519-SHA256-1.3.132.0.33 (nistp224, secp224r1)";
    reference
      "RFC 8732:
         Generic Security Service Application Program Interface
         (GSS-API) Key Exchange with SHA-2";
  }

  identity gss-curve25519-sha256-1.3.132.0.26 {
    base key-exchange-alg-base;
    description
      "GSS-CURVE25519-SHA256-1.3.132.0.26 (nistk233, sect233k1)";
    reference
      "RFC 8732:
         Generic Security Service Application Program Interface
         (GSS-API) Key Exchange with SHA-2";
  }

  identity gss-curve25519-sha256-1.3.132.0.27 {
    base key-exchange-alg-base;
    description
      "GSS-CURVE25519-SHA256-1.3.132.0.27 (nistb233, sect233r1)";
    reference
      "RFC 8732:
         Generic Security Service Application Program Interface
         (GSS-API) Key Exchange with SHA-2";
  }

  identity gss-curve25519-sha256-1.3.132.0.16 {
    base key-exchange-alg-base;
    description
      "GSS-CURVE25519-SHA256-1.3.132.0.16 (nistk283, sect283k1)";
    reference
      "RFC 8732:
         Generic Security Service Application Program Interface
         (GSS-API) Key Exchange with SHA-2";
  }

  identity gss-curve25519-sha256-1.3.132.0.36 {
    base key-exchange-alg-base;
    description
      "GSS-CURVE25519-SHA256-1.3.132.0.36 (nistk409, sect409k1)";
    reference
      "RFC 8732:
         Generic Security Service Application Program Interface
         (GSS-API) Key Exchange with SHA-2";
  }

  identity gss-curve25519-sha256-1.3.132.0.37 {
    base key-exchange-alg-base;
    description
      "GSS-CURVE25519-SHA256-1.3.132.0.37 (nistb409, sect409r1)";
    reference
      "RFC 8732:
         Generic Security Service Application Program Interface
         (GSS-API) Key Exchange with SHA-2";
  }

  identity gss-curve25519-sha256-1.3.132.0.38 {
    base key-exchange-alg-base;
    description
      "GSS-CURVE25519-SHA256-1.3.132.0.38 (nistt571, sect571k1)";
    reference
      "RFC 8732:
         Generic Security Service Application Program Interface
         (GSS-API) Key Exchange with SHA-2";
  }

  identity gss-curve25519-sha256-curve25519-sha256 {
    base key-exchange-alg-base;
    description
      "GSS-CURVE25519-SHA256-CURVE25519-SHA256";
    reference
      "RFC 8732:
         Generic Security Service Application Program Interface
         (GSS-API) Key Exchange with SHA-2";
  }

  identity gss-curve25519-sha256-curve448-sha512 {
    base key-exchange-alg-base;
    description
      "GSS-CURVE25519-SHA256-CURVE448-SHA512";
    reference
      "RFC 8732:
         Generic Security Service Application Program Interface
         (GSS-API) Key Exchange with SHA-2";
  }

  identity gss-curve448-sha512-nistp256 {
    base key-exchange-alg-base;
    description
      "GSS-CURVE448-SHA512-NISTP256 (secp256r1)";
    reference
      "RFC 8732:
         Generic Security Service Application Program Interface
         (GSS-API) Key Exchange with SHA-2";
  }

  identity gss-curve448-sha512-nistp384 {
    base key-exchange-alg-base;
    description
      "GSS-CURVE448-SHA512-NISTP384 (secp384r1)";
    reference
      "RFC 8732:
         Generic Security Service Application Program Interface
         (GSS-API) Key Exchange with SHA-2";
  }

  identity gss-curve448-sha512-nistp521 {
    base key-exchange-alg-base;
    description
      "GSS-CURVE448-SHA512-NISTP521 (secp521r1)";
    reference
      "RFC 8732:
         Generic Security Service Application Program Interface
         (GSS-API) Key Exchange with SHA-2";
  }

  identity gss-curve448-sha512-1.3.132.0.1 {
    base key-exchange-alg-base;
    description
      "GSS-CURVE448-SHA512-1.3.132.0.1 (nistk163, sect163k1)";
    reference
      "RFC 8732:
         Generic Security Service Application Program Interface
         (GSS-API) Key Exchange with SHA-2";
  }

  identity gss-curve448-sha512-1.2.840.10045.3.1.1 {
    base key-exchange-alg-base;
    description
      "GSS-CURVE448-SHA512-1.2.840.10045.3.1.1 (nistp192, secp192r1)";
    reference
      "RFC 8732:
         Generic Security Service Application Program Interface
         (GSS-API) Key Exchange with SHA-2";
  }

  identity gss-curve448-sha512-1.3.132.0.33 {
    base key-exchange-alg-base;
    description
      "GSS-CURVE448-SHA512-1.3.132.0.33 (nistp224, secp224r1)";
    reference
      "RFC 8732:
         Generic Security Service Application Program Interface
         (GSS-API) Key Exchange with SHA-2";
  }

  identity gss-curve448-sha512-1.3.132.0.26 {
    base key-exchange-alg-base;
    description
      "GSS-CURVE448-SHA512-1.3.132.0.26 (nistk233, sect233k1)";
    reference
      "RFC 8732:
         Generic Security Service Application Program Interface
         (GSS-API) Key Exchange with SHA-2";
  }

  identity gss-curve448-sha512-1.3.132.0.27 {
    base key-exchange-alg-base;
    description
      "GSS-CURVE448-SHA512-1.3.132.0.27 (nistb233, sect233r1)";
    reference
      "RFC 8732:
         Generic Security Service Application Program Interface
         (GSS-API) Key Exchange with SHA-2";
  }

  identity gss-curve448-sha512-1.3.132.0.16 {
    base key-exchange-alg-base;
    description
      "GSS-CURVE448-SHA512-1.3.132.0.16 (nistk283, sect283k1)";
    reference
      "RFC 8732:
         Generic Security Service Application Program Interface
         (GSS-API) Key Exchange with SHA-2";
  }

  identity gss-curve448-sha512-1.3.132.0.36 {
    base key-exchange-alg-base;
    description
      "GSS-CURVE448-SHA512-1.3.132.0.36 (nistk409, sect409k1)";
    reference
      "RFC 8732:
         Generic Security Service Application Program Interface
         (GSS-API) Key Exchange with SHA-2";
  }

  identity gss-curve448-sha512-1.3.132.0.37 {
    base key-exchange-alg-base;
    description
      "GSS-CURVE448-SHA512-1.3.132.0.37 (nistb409, sect409r1)";
    reference
      "RFC 8732:
         Generic Security Service Application Program Interface
         (GSS-API) Key Exchange with SHA-2";
  }

  identity gss-curve448-sha512-1.3.132.0.38 {
    base key-exchange-alg-base;
    description
      "GSS-CURVE448-SHA512-1.3.132.0.38 (nistt571, sect571k1)";
    reference
      "RFC 8732:
         Generic Security Service Application Program Interface
         (GSS-API) Key Exchange with SHA-2";
  }

  identity gss-curve448-sha512-curve25519-sha256 {
    base key-exchange-alg-base;
    description
      "GSS-CURVE448-SHA512-CURVE25519-SHA256";
    reference
      "RFC 8732:
         Generic Security Service Application Program Interface
         (GSS-API) Key Exchange with SHA-2";
  }

  identity gss-curve448-sha512-curve448-sha512 {
    base key-exchange-alg-base;
    description
      "GSS-CURVE448-SHA512-CURVE448-SHA512";
    reference
      "RFC 8732:
         Generic Security Service Application Program Interface
         (GSS-API) Key Exchange with SHA-2";
  }

  identity curve25519-sha256 {
    base key-exchange-alg-base;
    description
      "CURVE25519-SHA256";
    reference
      "RFC 8731:
         Secure Shell (SSH) Key Exchange Method
         Using Curve25519 and Curve448";
  }

  identity curve448-sha512 {
    base key-exchange-alg-base;
    description
      "CURVE448-SHA512";
    reference
      "RFC 8731:
         Secure Shell (SSH) Key Exchange Method
         Using Curve25519 and Curve448";
  }

  typedef key-exchange-algorithm-ref {
    type identityref {
      base key-exchange-alg-base;
    }
    description
      "A reference to a SSH key exchange algorithm identifier.";
  }

  container supported-algorithms {
    config false;
    description
      "A container for a list of key exchange algorithms
       supported by the server.";
    leaf-list supported-algorithm {
      type key-exchange-algorithm-ref;
      description
        "A key exchange algorithm supported by the server.";
    }
  }
}
