module bbf-ip-interfaces {
  yang-version 1.1;
  namespace "urn:bbf:yang:bbf-ip-interfaces";
  prefix bbf-ipif;

  import ietf-interfaces {
    prefix if;
  }
  import bbf-if-type {
    prefix bbfift;
  }

  organization
    "Broadband Forum <https://www.broadband-forum.org>
     Common YANG Work Area";
  contact
    "Comments or questions about this Broadband Forum YANG module
     should be directed to <mailto:help@broadband-forum.org>.

     Editor:      Shiya Ashraf, Nokia

     Editor:      Nick Hancock, Adtran

     Editor:      Kevin Noll, CableLabs

     Editor:      Ludwig Pauwels, Nokia

     PS Leader:   Aihua Guo, Futurewei

     WA Director: Joey Boyd, Adtran

     WA Director: Sven Ooghe, Nokia";
  description
    "This module contains a collection of YANG definitions for
     supporting the Broadband Forum requirements on the management of
     IP host interfaces as applicable to access network equipment. As
     such, this module is specific to access network equipment (e.g.,
     BBF-specified Access Nodes and FTTdp DPUs).

     Specifically, this module defines data nodes used to manage the
     linkage between a Layer 3 IP host interface and its underlying
     Layer 2 interface, i.e., a VLAN sub-interface or a Layer 2
     termination.

     Managing the Layer 2 and Layer 3 interfaces as separate
     interfaces results in statistics being reported both at Layer 2
     (frame) and at Layer 3 (packet).

     Copyright (c) 2017-2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a8; see
     the TR itself for full legal notices.";

  revision 2024-11-11 {
    description
      "Amendment 8.
       * Approval Date:    2024-11-11.
       * Publication Date: 2024-11-11.";
    reference
      "TR-383a8: Common YANG Modules for Access Networks
                 <https://www.broadband-forum.org/technical/download/
                          TR-383_Amendment-8.pdf>";
  }

  augment "/if:interfaces/if:interface" {
    description
      "Augment interface configuration for an IP interface.";
    container ipif-lower-layer {
      presence "Provides the lower-layer of the IP interface within the
       interface stack.";
      description
        "Data node to provide linkage between a Layer 3 IP host
         interface and its lower-layer, i.e. Layer 2, interface. This
         is necessary when the Layer 3 IP host interface is an
         interface that is managed independently of its lower-layer
         interface. Alternatively, the interface providing Layer 2
         connectivity, e.g., Layer 2 termination or VLAN
         sub-interface, may also simultaneously support the Layer 3
         IP host management via IPv4 and/or IPv6, meaning that this
         lower-layer configuration is not relevant.";
      leaf interface {
        type if:interface-ref;
        must "derived-from-or-self(/if:interfaces/if:interface[if:name = current()]/if:type,'bbfift:l2-termination') or derived-from-or-self(/if:interfaces/if:interface[if:name = current()]/if:type,'bbfift:vlan-sub-interface')" {
          error-message
            "The lower-layer of an IP interface interface is not a 'l2-termination', nor a 'vlan-sub-interface'.";
          description
            "Only allow Layer 2 termination or VLAN sub-interfaces
             as lower-layer for an IP interface.";
        }
        mandatory true;
        description
          "References the lower-layer interface.";
      }
    }
  }
}
