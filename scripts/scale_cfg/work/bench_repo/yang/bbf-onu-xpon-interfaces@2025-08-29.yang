module bbf-onu-xpon-interfaces {
  yang-version 1.1;
  namespace "urn:bbf:yang:bbf-onu-xpon-interfaces";
  prefix bbf-onu-xponif;

  import bbf-onus {
    prefix bbf-onus;
  }
  import bbf-onu-management {
    prefix bbf-onum;
  }
  import bbf-onu-if-type {
    prefix bbf-onuift;
  }
  import bbf-onu-interfaces {
    prefix bbf-onu-if;
  }
  import bbf-xponani-common {
    prefix bbf-xponanic;
  }
  import bbf-xpon-types {
    prefix bbf-xpon-types;
  }
  import bbf-onu-ani-common {
    prefix bbf-onuanic;
  }

  organization
    "Broadband Forum <https://www.broadband-forum.org>
     Fiber Access Networks Work Area";
  contact
    "Comments or questions about this Broadband Forum YANG module
     should be directed to <mailto:info@broadband-forum.org>.

     Editor:      Joey Boyd, Adtran

     Editor:      Robert Peschi, Nokia

     PS Leader:   Joey Boyd, Adtran

     WA Director: Marta Seda, Calix";
  description
    "This module contains a collection of YANG definitions for
     supporting the Broadband Forum requirements on the management of
     Optical Network Units (ONUs).

     Specifically, this module defines xPON system augments for the
     management of the Optical Network Unit (ONU).

     This module is based on definitions provided in:
       - module bbf-xponani, revision 2023-06-21, TR-385
         Issue 2 Amendment1.

     Copyright (c) 2018-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-505; see
     the WT itself for full legal notices.";

  revision 2025-08-29 {
    description
      "TBD.
       * Approval Date:    TBD.
       * Publication Date: TBD.";
    reference
      "TBD";
  }

  augment "/bbf-onus:onus/bbf-onum:onu/bbf-onum:data-stand-alone-instance/bbf-onu-if:interfaces/bbf-onu-if:interface" {
    when "derived-from-or-self(bbf-onu-if:type,'bbf-onuift:ani')";
    description
      "Intended for a stand-alone ONU instance.

       Augment interface configuration with xPON Access Newtork
       Interface (ANI) configuration.

       The ANI represents the Optical Network Unit (ONU) device.";
    container ani {
      description
        "ANI configuration.";
      uses bbf-xponanic:ani-config-data {
        refine "upstream-fec" {
          default "false";
        }
        refine "management-gemport-aes-indicator" {
          default "false";
        }
        refine "notifiable-defect" {
          if-feature "bbf-xponanic:ani-defect-notifications";
        }
      }
      uses bbf-onuanic:back-pressure-config {
        refine "back-pressure-to-unis/enabled" {
          default "true";
        }
        refine "back-pressure-to-unis/duration" {
          default "0";
        }
      }
      leaf onu-id {
        if-feature "bbf-xponanic:configurable-ani-onu-id";
        type bbf-xpon-types:onu-id;
        description
          "The TC layer ONU Identifier (ONU-ID). When configured this
           is the value which the Optical Line Termination (OLT) must
           assign to the Optical Network Unit (ONU) during the ONU's
           activation using the Assign_ONU-ID Physical Layer
           Operations, Administrations and Maintenance (PLOAM)
           message.

           For G-PON, range is 0..253.
           For XG-PON, range is 0..1022.
           For XGS-PON, range is 0..1020.
           For NG-PON2, range is 0..1020.
           For 25GS-PON, range is 0..1018.
           For 50G-PON, range is 0..1019.";
        reference
          "ITU-T G.984.3 Clause 5.5.2;
           ITU-T G.987.3 Clause 6.4.2;
           ITU-T G.9807.1 Clause C.6.1.5.6;
           ITU-T G.989.3 Clause 6.1.5.6;
           ITU-T G.9804.2 Clause 6.5.2.5;
           MSA 25GS-PON Section C.6.1.5.7";
      }
      leaf management-gemport-id {
        if-feature "bbf-xponanic:configurable-ani-management-gem-port-id";
        type uint32;
        description
          "This leaf is only relevant to G-PON ONUs; it is ignored for
           non-G-PON ONUs. In contrast with other xPON technologies,
           in the case of G-PON, there is no requirement that the
           ITU-T TC ID of the management G-PON Encapsulation Method
           (GEM) port for the Optical Network Unit (ONU) is
           numerically equal to the ONU-ID. This leaf provides the
           capability to specify value for the management GEM port ID.

           If this leaf is not configured the management GEM port
           ID must be numerically equal to the ONU-ID.";
        reference
          "ITU-T G.984.3 Clause 5.5.5 - OMCC Port-ID;
           ITU-T G.987.3 Clause 6.4.4 - OMCC Port-ID;
           ITU-T G.989.3 Clause 6.1.5.8 - OMCC Port-ID;
           ITU-T G.9807.1 Clause C.6.1.5.8 - OMCC Port-ID;
           ITU-T G.9804.2 Clause 6.5.2.7 - OMCC Port-ID";
      }
    }
  }
  augment "/bbf-onus:onus/bbf-onum:onu/bbf-onum:data-stand-alone-instance/bbf-onu-if:interfaces-state/bbf-onu-if:interface" {
    when "derived-from-or-self(bbf-onu-if:type,'bbf-onuift:ani')";
    description
      "Intended for a stand-alone ONU instance.

       Augment interface state data with xPON Access Network Interface
       (ANI) state data.

       The ANI represents the Optical Network Unit (ONU) device.";
    container ani {
      config false;
      description
        "State data for ANI interface.";
      uses bbf-xponanic:ani-state-data {
        refine "onu-serial-number" {
          if-feature "bbf-xponanic:ani-onu-serial-number-reporting-alt";
        }
        refine "active-defects" {
          if-feature "bbf-xponanic:ani-defects";
        }
      }
    }
  }
  augment "/bbf-onus:onus/bbf-onum:onu/bbf-onum:data-instance-from-template/bbf-onu-if:interfaces/bbf-onu-if:interface" {
    when "derived-from-or-self(bbf-onu-if:type,'bbf-onuift:ani')";
    description
      "Intended for an ONU instance derived from template(s).

       Augment interface configuration with xPON Access Newtork
       Interface (ANI) configuration.

       The ANI represents the Optical Network Unit (ONU) device.";
    container ani {
      description
        "ANI configuration.";
      uses bbf-xponanic:ani-config-data {
        refine "notifiable-defect" {
          if-feature "bbf-xponanic:ani-defect-notifications";
        }
      }
      uses bbf-onuanic:back-pressure-config;
      leaf onu-id {
        if-feature "bbf-xponanic:configurable-ani-onu-id";
        type bbf-xpon-types:onu-id;
        description
          "The TC layer ONU Identifier (ONU-ID). When configured this
           is the value which the Optical Line Termination (OLT) must
           assign to the Optical Network Unit (ONU) during the ONU's
           activation using the Assign_ONU-ID Physical Layer
           Operations, Administrations and Maintenance (PLOAM)
           message.

           For G-PON, range is 0..253.
           For XG-PON, range is 0..1022.
           For XGS-PON, range is 0..1020.
           For NG-PON2, range is 0..1020.
           For 25GS-PON, range is 0..1018.
           For 50G-PON, range is 0..1019.";
        reference
          "ITU-T G.984.3 Clause 5.5.2;
           ITU-T G.987.3 Clause 6.4.2;
           ITU-T G.9807.1 Clause C.6.1.5.6;
           ITU-T G.989.3 Clause 6.1.5.6;
           ITU-T G.9804.2 Clause 6.5.2.5;
           MSA 25GS-PON Section C.6.1.5.7";
      }
      leaf management-gemport-id {
        if-feature "bbf-xponanic:configurable-ani-management-gem-port-id";
        type uint32;
        description
          "This leaf is only relevant to G-PON ONUs; it is ignored for
           non-G-PON ONUs. In contrast with other xPON technologies,
           in the case of G-PON, there is no requirement that the
           ITU-T TC ID of the management G-PON Encapsulation Method
           (GEM) port for the Optical Network Unit (ONU) is
           numerically equal to the ONU-ID. This leaf provides the
           capability to specify value for the management GEM port ID.

           If this leaf is not configured the management GEM port
           ID must be numerically equal to the ONU-ID.";
        reference
          "ITU-T G.984.3 Clause 5.5.5 - OMCC Port-ID;
           ITU-T G.987.3 Clause 6.4.4 - OMCC Port-ID;
           ITU-T G.989.3 Clause 6.1.5.8 - OMCC Port-ID;
           ITU-T G.9807.1 Clause C.6.1.5.8 - OMCC Port-ID;
           ITU-T G.9804.2 Clause 6.5.2.7 - OMCC Port-ID";
      }
    }
  }
  augment "/bbf-onus:onus/bbf-onum:onu/bbf-onum:data-instance-from-template/bbf-onu-if:interfaces-state/bbf-onu-if:interface" {
    when "derived-from-or-self(bbf-onu-if:type,'bbf-onuift:ani')";
    description
      "Intended for an ONU instance derived from template(s).

       Augment interface state data with xPON Access Network Interface
       (ANI) state data.

       The ANI represents the Optical Network Unit (ONU) device.";
    container ani {
      config false;
      description
        "State data for ANI interface.";
      uses bbf-xponanic:ani-state-data {
        refine "onu-serial-number" {
          if-feature "bbf-xponanic:ani-onu-serial-number-reporting-alt";
        }
        refine "active-defects" {
          if-feature "bbf-xponanic:ani-defects";
        }
      }
    }
  }
  augment "/bbf-onus:onus/bbf-onum:template/bbf-onum:data/bbf-onu-if:interfaces/bbf-onu-if:interface" {
    when "derived-from-or-self(bbf-onu-if:type,'bbf-onuift:ani')";
    description
      "Intended for an ONU template.
       Augment interface configuration with xPON Access Newtork
       Interface (ANI) configuration.

       The ANI represents the Optical Network Unit (ONU) device.";
    container ani {
      description
        "ANI configuration.";
      uses bbf-xponanic:ani-config-data {
        refine "upstream-fec" {
          default "false";
        }
        refine "management-gemport-aes-indicator" {
          default "false";
        }
        refine "notifiable-defect" {
          if-feature "bbf-xponanic:ani-defect-notifications";
        }
      }
      uses bbf-onuanic:back-pressure-config {
        refine "back-pressure-to-unis/enabled" {
          default "true";
        }
        refine "back-pressure-to-unis/duration" {
          default "0";
        }
      }
    }
  }
}
