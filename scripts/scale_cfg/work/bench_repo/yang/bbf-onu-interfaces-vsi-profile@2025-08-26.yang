module bbf-onu-interfaces-vsi-profile {
  yang-version 1.1;
  namespace "urn:bbf:yang:bbf-onu-interfaces-vsi-profile";
  prefix bbf-onu-if-vsi-prof;

  import bbf-onus {
    prefix bbf-onus;
  }
  import bbf-onu-management {
    prefix bbf-onum;
  }
  import bbf-onu-interfaces {
    prefix bbf-onu-if;
  }
  import bbf-onu-if-type {
    prefix bbf-onuift;
  }
  import bbf-onu-vlan-sub-interface-profiles {
    prefix bbf-onu-vsi-prof;
  }
  import bbf-vlan-sub-interface-profile-fp {
    prefix bbf-vsi-prof-fp;
  }

  organization
    "Broadband Forum <https://www.broadband-forum.org>
     Common YANG Work Area";
  contact
    "Comments or questions about this Broadband Forum YANG module
     should be directed to <mailto:help@broadband-forum.org>.

     Editor:      Joey Boyd, Adtran

     Editor:      Robert Peschi, Nokia

     PS Leader:   Joey Boyd, Adtran

     WA Director: Marta Seda, Calix";
  description
    "This module contains a collection of YANG definitions for
     supporting the Broadband Forum requirements on the management of
     Optical Network Units (ONUs).

     Specifically, this module augments an Optical Network Unit (ONU)
     VLAN sub-interface with a reference to a VLAN sub-interface
     profile.

     This module is based on definitions provided in:
     - bbf-vlan-sub-interface-profiles.yang, TR-383 Amendment 6;
     - bbf-vlan-sub-interface-profile-fp.yang, TR-383 Amendment 6.

     Copyright (c) 2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-505; see the WT
     itself for full legal notices.";

  revision 2025-08-26 {
    description
      "TBD
       * Approval Date:    TBD.
       * Publication Date: TBD.";
    reference
      "TBD";
  }

  feature shared-vsi-profiles {
    description
      "Indicates support for shared VLAN sub-interfaces profiles.";
  }

  augment "/bbf-onus:onus/bbf-onum:onu/bbf-onum:data-stand-alone-instance/bbf-onu-if:interfaces/bbf-onu-if:interface" {
    when "derived-from-or-self(bbf-onu-if:type, 'bbf-onuift:vlan-sub-interface')" {
      description
        "Common optional data for VLAN sub-interfaces.";
    }
    description
      "Intended for a stand-alone ONU instance (i.e., that does not
       rely on any template).

       Add data nodes for a VLAN sub-interface.";
    choice configuration-method {
      description
        "Provides methods for configuring VLAN sub-interface data.";
      case shared-profile {
        if-feature "shared-vsi-profiles";
        description
          "Provides data nodes in case a shared VLAN sub-interfaces
           profile is used.";
        container vsi-profile {
          presence "Presence indicates a VLAN sub-interface profile is to be
           applied.";
          description
            "Data nodes for when a VLAN sub-interface profile is to be
             applied.

             Note that from YANG model perspective the same data can
             be configured directly within a VLAN sub-interface, or
             can be configured indirectly in a VLAN sub-interface
             using the referenced profile.

             Note that the YANG definition also allows the direct and
             indirect configuration to coexist. In that case the
             direct configuration (within the VLAN sub-interface
             itself) always has priority on the indirect configuration
             through the data nodes in the referenced profile.";
          leaf vsi-profile {
            type leafref {
              path "/bbf-onus:onus/bbf-onu-vsi-prof:vsi-profiles/bbf-onu-vsi-prof:vsi-profile/bbf-onu-vsi-prof:name";
            }
            mandatory true;
            description
              "A reference to a VLAN sub-interface profile.";
          }
          uses bbf-vsi-prof-fp:parameterized-vlan-tag {
            refine "tag-0/vlan-id" {
              mandatory true;
            }
            refine "tag-1/vlan-id" {
              mandatory true;
            }
            refine "ingress-rewrite-tag-0/vlan-id" {
              if-feature "bbf-onu-vsi-prof:vlan-id-translation";
              mandatory true;
            }
            refine "ingress-rewrite-tag-1/vlan-id" {
              if-feature "bbf-onu-vsi-prof:vlan-id-translation";
              mandatory true;
            }
            refine "egress-rewrite-tag-0/vlan-id" {
              if-feature "bbf-onu-vsi-prof:vlan-id-translation";
              default "vlan-id-from-match";
            }
            refine "egress-rewrite-tag-1/vlan-id" {
              if-feature "bbf-onu-vsi-prof:vlan-id-translation";
              default "vlan-id-from-match";
            }
          }
        }
      }
    }
  }
  augment "/bbf-onus:onus/bbf-onum:onu/bbf-onum:data-instance-from-template/bbf-onu-if:interfaces/bbf-onu-if:interface" {
    when "derived-from-or-self(bbf-onu-if:type, 'bbf-onuift:vlan-sub-interface')" {
      description
        "Common optional data for VLAN sub-interfaces.";
    }
    description
      "Intended for an ONU instance derived from template(s).

       Add data nodes for a VLAN sub-interface.";
    choice configuration-method {
      description
        "Provides methods for configuring VLAN sub-interface data.";
      case shared-profile {
        if-feature "shared-vsi-profiles";
        description
          "Provides data nodes in case a shared VLAN sub-interfaces
           profile is used.";
        container vsi-profile {
          presence "Presence indicates a VLAN sub-interface profile is to be
           applied.";
          description
            "Data nodes for when a VLAN sub-interface profile is to be
             applied.

             Note that from YANG model perspective the same data can
             be configured directly within a VLAN sub-interface, or
             can be configured indirectly in a VLAN sub-interface
             using the referenced profile.

             Note that the YANG definition also allows the direct and
             indirect configuration to coexist. In that case the
             direct configuration (within the VLAN sub-interface
             itself) always has priority on the indirect configuration
             through the data nodes in the referenced profile.";
          leaf vsi-profile {
            type leafref {
              path "/bbf-onus:onus/bbf-onu-vsi-prof:vsi-profiles/bbf-onu-vsi-prof:vsi-profile/bbf-onu-vsi-prof:name";
            }
            mandatory true;
            description
              "A reference to a VLAN sub-interface profile.";
          }
          uses bbf-vsi-prof-fp:parameterized-vlan-tag {
            refine "tag-0/vlan-id" {
              mandatory true;
            }
            refine "tag-1/vlan-id" {
              mandatory true;
            }
            refine "ingress-rewrite-tag-0/vlan-id" {
              if-feature "bbf-onu-vsi-prof:vlan-id-translation";
              mandatory true;
            }
            refine "ingress-rewrite-tag-1/vlan-id" {
              if-feature "bbf-onu-vsi-prof:vlan-id-translation";
              mandatory true;
            }
            refine "egress-rewrite-tag-0/vlan-id" {
              if-feature "bbf-onu-vsi-prof:vlan-id-translation";
              default "vlan-id-from-match";
            }
            refine "egress-rewrite-tag-1/vlan-id" {
              if-feature "bbf-onu-vsi-prof:vlan-id-translation";
              default "vlan-id-from-match";
            }
          }
        }
      }
    }
  }
  augment "/bbf-onus:onus/bbf-onum:template/bbf-onum:data/bbf-onu-if:interfaces/bbf-onu-if:interface" {
    when "derived-from-or-self(bbf-onu-if:type, 'bbf-onuift:vlan-sub-interface')" {
      description
        "Common optional data for VLAN sub-interfaces.";
    }
    description
      "Intended for an ONU template.

       Add data nodes for a VLAN sub-interface.";
    choice configuration-method {
      description
        "Provides methods for configuring VLAN sub-interface data.";
      case shared-profile {
        if-feature "shared-vsi-profiles";
        description
          "Provides data nodes in case a shared VLAN sub-interfaces
           profile is used.";
        container vsi-profile {
          presence "Presence indicates a VLAN sub-interface profile is to be
           applied.";
          description
            "Data nodes for when a VLAN sub-interface profile is to be
             applied.

             Note that from YANG model perspective the same data can
             be configured directly within a VLAN sub-interface, or
             can be configured indirectly in a VLAN sub-interface
             using the referenced profile.

             Note that the YANG definition also allows the direct and
             indirect configuration to coexist. In that case the
             direct configuration (within the VLAN sub-interface
             itself) always has priority on the indirect configuration
             through the data nodes in the referenced profile.";
          leaf vsi-profile {
            type leafref {
              path "/bbf-onus:onus/bbf-onu-vsi-prof:vsi-profiles/bbf-onu-vsi-prof:vsi-profile/bbf-onu-vsi-prof:name";
            }
            mandatory true;
            description
              "A reference to a VLAN sub-interface profile.";
          }
          uses bbf-vsi-prof-fp:parameterized-vlan-tag {
            refine "tag-0/vlan-id" {
              mandatory true;
            }
            refine "tag-1/vlan-id" {
              mandatory true;
            }
            refine "ingress-rewrite-tag-0/vlan-id" {
              if-feature "bbf-onu-vsi-prof:vlan-id-translation";
              mandatory true;
            }
            refine "ingress-rewrite-tag-1/vlan-id" {
              if-feature "bbf-onu-vsi-prof:vlan-id-translation";
              mandatory true;
            }
            refine "egress-rewrite-tag-0/vlan-id" {
              if-feature "bbf-onu-vsi-prof:vlan-id-translation";
              default "vlan-id-from-match";
            }
            refine "egress-rewrite-tag-1/vlan-id" {
              if-feature "bbf-onu-vsi-prof:vlan-id-translation";
              default "vlan-id-from-match";
            }
          }
        }
      }
    }
  }
}
