module bbf-ringing-patterns-common {
  yang-version 1.1;
  namespace "urn:bbf:yang:bbf-ringing-patterns-common";
  prefix bbf-rpc;

  import bbf-voip-types {
    prefix bbf-voip-tp;
  }

  organization
    "Broadband Forum <https://www.broadband-forum.org>
     Provider Cloud Work Area";
  contact
    "Comments or questions about this Broadband Forum YANG module
     should be directed to <mailto:info@broadband-forum.org>.

     Editor:      Shiya Ashraf, Nokia

     Editor:      Kevin Noll, CableLabs

     PS Leader:   Sven Ooghe, Nokia

     PS Leader:   Joey Boyd, Adtran

     WA Director: Bruno Cornaglia, Vodafone

     WA Director: Mengmeng Li, China Mobile

     WA Director: Haomian Zheng, Huawei";
  description
    "This module contains a collection of YANG definitions for
     supporting the Broadband Forum requirements on voice service
     management. As such, this module is specific to access
     network equipment (e.g., BBF-specified Access Nodes and FTTdp
     DPUs).

     Specifically, this module describes reusable groupings containing
     configuration and operational data nodes used for managing
     ringing patterns.

     Copyright (c) 2017-2025, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a9; see
     the TR itself for full legal notices.";

  revision 2025-07-02 {
    description
      "Amendment 9.
       * Approval Date:    2025-07-02.
       * Publication Date: 2025-07-02.";
    reference
      "TR-383a9: Common YANG Modules for Access Networks
                 <https://www.broadband-forum.org/technical/download/
                          TR-383_Amendment-9.pdf>";
  }

  grouping ringing-components {
    description
      "Data nodes to configure ringing components.";
    container ringing-components {
      must "not(boolean(ringing-component)) or ringing-component[not(../ringing-component/position> position)]/position <= count(current()/ringing-component)" {
        error-message
          "The values configured for ringing component positions within a ringing pattern are not consecutive integers beginning at 1.";
        description
          "Ensure that all position values are consecutive, beginning
           with the value 1.";
      }
      must "(count(ringing-component) != 1) or not(boolean(ringing-component[position=1])) or (ringing-component[position=1]/ringing-on = 'true')" {
        error-message
          "The ringing pattern comprises only one ringing component, but the ringing component does not switch on ringing; it is just a period of silence.";
        description
          "Ensure that the ringing pattern actually switches on
           ringing.";
      }
      description
        "Data nodes to manage ringing components of a ringing
         pattern.";
      list ringing-component {
        must "(count(../ringing-component) = 1) or (position = 1) or not(boolean(../ringing-component[position=current()/position - 1])) or (../ringing-component[position=current()/position - 1]/ringing-on != ringing-on)" {
          error-message
            "The ringing pattern defines two or more sequential ringing components that do not alternate between ringing and silence.";
          description
            "Prevent the configuration of two sequential ringing
             components that are both periods of silence.

             This error is not possible if only one ringing component
             has been configured or if the ringing component is the
             first ringing component as it will have no preceding
             ringing component, so the must statement evaluates to
             'true' in these cases.

             Since this must statement is designed to specifically
             report to the client that two sequential ringing
             components that are both periods of silence are being
             configured, the must statement also tests for invalid
             configurations that will be caught by other must
             statements or YANG syntax validation to prevent this
             error from being reported and avoid the client being
             inundated with irrelevant error messages unnecessarily
             in the following cases:
             - if the preceding ringing component does not exist as
               this error will be caught by the must statement that
               checks for non-consecutive values for leaf 'position'.
             - if the leaf 'position' is empty, this will be caught by
               YANG syntax validation.";
        }
        key "position";
        min-elements 1;
        description
          "A ringing component of the ringing pattern.";
        leaf position {
          type uint8 {
            range "1..max";
          }
          description
            "The position of this ringing component within the ringing
             pattern, whereby ringing components of a ringing pattern
             are to be played in ascending order from the value of 1
             based on the value of this leaf.

             Note that the values of position within a ringing pattern
             must be consecutive beginning from the value 1; this aids
             validation of the ringing pattern configuration.";
        }
        leaf duration {
          type union {
            type enumeration {
              enum "continuous" {
                description
                  "The ringing component is to be played continuously.

                   Note that to be played continuously, the ringing
                   component must be the last ringing component within
                   the ringing pattern and not silence.";
              }
            }
            type uint16 {
              range "1..max";
            }
          }
          units "milliseconds";
          must "(. != 'continuous') or (../ringing-on = 'true')" {
            error-message
              "A ringing component is continuous, but ringing is not switched on.";
            description
              "Ensure that if the ringing component is set to ring
               continuously that ringing is switched on.";
          }
          must "(.!='continuous') or (../position = count(../../ringing-component))" {
            error-message
              "A continuous ringing component is not the last ringing component defined within a ringing pattern.";
            description
              "Ensure that if the duration is set to 'continuous',
               the ringing component is the last ringing component
               in the ringing pattern.";
          }
          mandatory true;
          description
            "The duration in milliseconds the ringing component is
             to be played.";
          reference
            "ITU-T G.988 Clause 9.9.6 - Ringing pattern table,
             Duration";
        }
        leaf ringing-on {
          type boolean;
          mandatory true;
          description
            "If 'true', ringing is switched on for this ringing
             component.";
          reference
            "ITU-T G.988 Clause 9.9.6 - Ringing pattern table,
             Ringing on";
        }
      }
      container repetition-behavior {
        when "(count(../ringing-component) > 1) and ../ringing-component[position=count(../ringing-component)]/duration != 'continuous'" {
          description
            "Only applicable if the ringing pattern comprises more
             than 1 ringing component and the last ringing component
             is not a continuous ringing component.";
        }
        description
          "Manages the repetition behavior for ringing patterns
           comprising more than one ringing component, if and only if
           the last ringing component is not to be played
           continuously.

           Note that if a ringing pattern is comprised of a single
           ringing component, no configuration for repetition behavior
           is needed; the ringing component will either have a
           duration set to 'continuous', in which case it is to be
           repeated continuously, or it has a finite duration, in
           which case it is to be played only once, i.e., is not to be
           repeated.";
        leaf repeat-from-position {
          type union {
            type enumeration {
              enum "do-not-repeat" {
                description
                  "The ringing pattern is not to be repeated, i.e.,
                   the entire ringing pattern is to be played just
                   once.";
              }
            }
            type uint8 {
              range "1..max";
            }
          }
          must "(.='do-not-repeat') or (. < count(../../ringing-component))" {
            error-message
              "The position from which the ringing pattern is to be repeated is invalid.";
            description
              "Ensure that the value for position is valid.";
          }
          mandatory true;
          description
            "Indicates the position within the ringing pattern from
             which the ringing components are to be repeated
             continuously after being played in their entirety once
             until interrupted by some other event.

             If set to 1, the entire ringing pattern is to be repeated
             continuously.";
        }
      }
    }
  }

  grouping ringing-pattern-files {
    description
      "Data nodes to manage ringing pattern definitions located in a
       file.";
    container file {
      description
        "Configuration to access to the ringing pattern file.";
      choice location {
        mandatory true;
        description
          "Selects the location of the file containing the ringing
           pattern definition.";
        case url {
          leaf url {
            type bbf-voip-tp:voip-uri;
            description
              "Path and file name of a file containing a ringing tone
               to be played out.";
            reference
              "ITU-T G.988 Clause 9.9.6 - Ringing event table,
               Ringing file";
          }
        }
      }
      leaf number-of-plays {
        type union {
          type uint8 {
            range "1..max";
          }
          type enumeration {
            enum "continuous" {
              description
                "The pattern defined by the contents of the file is to
                 be repeated continuously until interrupted by some
                 other event.";
            }
          }
        }
        default "1";
        description
          "Number of times the ringing pattern defined by the contents
           of the file is to be repeated.";
        reference
          "ITU-T G.988 Clause 9.9.6 - Ringing event table,
           Ringing file repetitions";
      }
    }
  }

  grouping ringing-patterns {
    description
      "Data nodes used for configuring the ringing patterns.

       Note that this grouping intended to be augmented at the
       position it is used to add the functionality required of the
       specific implementation through the use of the other groupings
       located within this module, i.e., the groupings
       'ringing-components' and/or 'ringing-pattern-files'.

       If more than one of these groupings is used then the uses
       statements should be included within a choice statement, with
       the choice named 'source' and the cases named according to the
       name of groupings.

       This strategy enables distinct implementations to add the
       required functionality according to their specific
       requirements.";
    container ringing-patterns {
      description
        "Data nodes to define and manage ringing patterns.";
      list ringing-pattern {
        key "name";
        description
          "A ringing pattern.";
        reference
          "ITU-T G.988 Clause 9.9.6 - Ringing pattern table";
        leaf name {
          type string;
          description
            "The name of the ringing pattern.";
        }
      }
    }
  }
}
