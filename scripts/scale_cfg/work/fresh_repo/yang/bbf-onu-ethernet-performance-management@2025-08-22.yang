module bbf-onu-ethernet-performance-management {
  yang-version 1.1;
  namespace "urn:bbf:yang:bbf-onu-ethernet-performance-management";
  prefix bbf-onu-eth-pm;

  import bbf-onus {
    prefix bbf-onus;
  }
  import bbf-onu-management {
    prefix bbf-onum;
  }
  import bbf-onu-interfaces {
    prefix bbf-onu-if;
  }
  import bbf-onu-if-type {
    prefix bbf-onuift;
  }
  import bbf-onu-interfaces-performance-management {
    prefix bbf-onu-if-pm;
  }
  import bbf-ethernet-performance-management-common {
    prefix bbf-eth-pmc;
  }

  organization
    "Broadband Forum <https://www.broadband-forum.org>
     Common YANG Work Area";
  contact
    "Comments or questions about this Broadband Forum YANG module
     should be directed to <mailto:help@broadband-forum.org>.

     Editor:      Nick Hancock, Adtran

     Editor:      Ludwig Pauwels, Nokia

     PS Leader:   Joey Boyd, Adtran

     WA Director: Joey Boyd, Adtran

     WA Director: Sven Ooghe, Nokia";
  description
    "This module contains a collection of YANG definitions for
     supporting the Broadband Forum requirements on the management of
     Optical Network Units (ONUs).

     Specifically, this module the interface performance monitoring
     data nodes with Ethernet interface specific data nodes.

     This module is based on definitions provided in:
     - bbf-ethernet-performance-management, TR-383 Amendment 7.

     Copyright (c) 2017-2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-505; see the WT
     itself for full legal notices.";

  revision 2025-08-22 {
    description
      "TBD
       * Approval Date:    TBD.
       * Publication Date: TBD.";
    reference
      "TBD";
  }

  feature in-undersize-pkts {
    description
      "Indicates support for reporting the number of received
       undersized frames.";
  }

  augment "/bbf-onus:onus/bbf-onum:onu/bbf-onum:data-stand-alone-instance/bbf-onu-if:interfaces-state/bbf-onu-if:interface/bbf-onu-if-pm:performance/bbf-onu-if-pm:intervals-15min/bbf-onu-if-pm:history" {
    when "derived-from-or-self(../../../bbf-onu-if:type,
                          'bbf-onuift:ethernetCsmacd')" {
      description
        "Only applicable to Ethernet interfaces.";
    }
    description
      "Augment the historic 15 minute interface performance counts
       with Ethernet specific attributes.";
    container ethernet {
      description
        "Historic 15 minute Ethernet performance counters.";
      uses bbf-eth-pmc:eth-interface-performance-counters {
        refine "in-undersize-pkts" {
          if-feature "bbf-onu-eth-pm:in-undersize-pkts";
        }
      }
    }
  }
  augment "/bbf-onus:onus/bbf-onum:onu/bbf-onum:data-stand-alone-instance/bbf-onu-if:interfaces-state/bbf-onu-if:interface/bbf-onu-if-pm:performance/bbf-onu-if-pm:intervals-24hr/bbf-onu-if-pm:history" {
    when "derived-from-or-self(../../../bbf-onu-if:type,
                          'bbf-onuift:ethernetCsmacd')" {
      description
        "Only applicable to Ethernet interfaces.";
    }
    if-feature "bbf-onu-if-pm:performance-24hr";
    description
      "Augment the historic 24 hour interface performance counts with
       Ethernet specific attributes.";
    container ethernet {
      description
        "Historic 24 hour Ethernet performance counters.";
      uses bbf-eth-pmc:eth-interface-performance-counters {
        refine "in-undersize-pkts" {
          if-feature "bbf-onu-eth-pm:in-undersize-pkts";
        }
      }
    }
  }
  augment "/bbf-onus:onus/bbf-onum:onu/bbf-onum:data-instance-from-template/bbf-onu-if:interfaces-state/bbf-onu-if:interface/bbf-onu-if-pm:performance/bbf-onu-if-pm:intervals-15min/bbf-onu-if-pm:history" {
    when "derived-from-or-self(../../../bbf-onu-if:type,
                          'bbf-onuift:ethernetCsmacd')" {
      description
        "Only applicable to Ethernet interfaces.";
    }
    description
      "Augment the historic 15 minute interface performance counts
       with Ethernet specific attributes.";
    container ethernet {
      description
        "Historic 15 minute Ethernet performance counters.";
      uses bbf-eth-pmc:eth-interface-performance-counters {
        refine "in-undersize-pkts" {
          if-feature "bbf-onu-eth-pm:in-undersize-pkts";
        }
      }
    }
  }
  augment "/bbf-onus:onus/bbf-onum:onu/bbf-onum:data-instance-from-template/bbf-onu-if:interfaces-state/bbf-onu-if:interface/bbf-onu-if-pm:performance/bbf-onu-if-pm:intervals-24hr/bbf-onu-if-pm:history" {
    when "derived-from-or-self(../../../bbf-onu-if:type,
                          'bbf-onuift:ethernetCsmacd')" {
      description
        "Only applicable to Ethernet interfaces.";
    }
    if-feature "bbf-onu-if-pm:performance-24hr";
    description
      "Augment the historic 24 hour interface performance counts with
       Ethernet specific attributes.";
    container ethernet {
      description
        "Historic 24 hour Ethernet performance counters.";
      uses bbf-eth-pmc:eth-interface-performance-counters {
        refine "in-undersize-pkts" {
          if-feature "bbf-onu-eth-pm:in-undersize-pkts";
        }
      }
    }
  }
}
