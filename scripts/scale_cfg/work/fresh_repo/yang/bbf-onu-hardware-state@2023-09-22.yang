module bbf-onu-hardware-state {
  yang-version 1.1;
  namespace "urn:bbf:yang:bbf-onu-hardware-state";
  prefix bbf-onu-hw-st;

  import bbf-onus {
    prefix bbf-onus;
  }
  import bbf-onu-management {
    prefix bbf-onum;
  }
  import bbf-hardware-common {
    prefix bbf-hwc;
  }

  organization
    "Broadband Forum <https://www.broadband-forum.org>
     Common YANG Work Area";
  contact
    "Comments or questions about this Broadband Forum YANG module
     should be directed to <mailto:help@broadband-forum.org>.

     Editor:      Joey Boyd, Adtran

     Editor:      Robert Peschi, Nokia

     PS Leader:   Joey Boyd, Adtran

     WA Director: Marta Seda, Calix";
  description
    "This module contains a collection of YANG definitions for
     supporting the Broadband Forum requirements on the management of
     Optical Network Units (ONUs).

     Specifically, this module defines data nodes for reporting on
     detected hardware components in a non-NMDA environment.

     This module is based on definitions provided in:
     - ietf-hardware.yang, revision 2018-03-13, RFC 8348.
     (Note, the baseline is not ietf-hardware-state.yang. This defines
     the same data nodes with the qualification 'deprecated'.)

     Copyright (c) 2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-505; see the WT
     itself for full legal notices.";

  revision 2023-09-22 {
    description
      "TBD
       * Approval Date:    TBD.
       * Publication Date: TBD.";
    reference
      "TBD";
  }

  feature entity-mib {
    description
      "This feature indicates that the device implements the
       ENTITY-MIB.";
    reference
      "RFC 6933: Entity MIB (Version 4)";
  }

  feature hardware-state {
    description
      "Indicates that ENTITY-STATE-MIB objects are supported.";
    reference
      "RFC 4268: Entity State MIB";
  }

  feature hardware-sensor {
    description
      "Indicates that ENTITY-SENSOR-MIB objects are supported.";
    reference
      "RFC 3433: Entity Sensor Management Information Base";
  }

  augment "/bbf-onus:onus/bbf-onum:onu/bbf-onum:data-stand-alone-instance" {
    description
      "R/O hardware augments for a stand-alone ONU instance.";
    uses bbf-hwc:hardware-config {
      refine "hardware" {
        config false;
      }
      refine "hardware/component/state" {
        if-feature "hardware-state";
      }
      augment "hardware" {
        description
          "Augments the 'hardware' container.";
        uses bbf-hwc:hardware-config-false;
      }
      augment "hardware/component" {
        description
          "Augments an element in the hardware component's list.";
        uses bbf-hwc:hardware-component-config-false {
          refine "physical-index" {
            if-feature "entity-mib";
          }
          refine "sensor-data" {
            if-feature "hardware-sensor";
          }
        }
      }
      augment "hardware/component/state" {
        description
          "Augments the hardware component's 'state' container.";
        uses bbf-hwc:hardware-component-state-config-false;
      }
    }
    notification hardware-state-change {
      description
        "A hardware-state-change notification is generated when the
         value of /hardware/last-change changes in the operational
         state.";
      reference
        "RFC 6933: Entity MIB (Version 4) - entConfigChange";
    }
  }
  augment "/bbf-onus:onus/bbf-onum:onu/bbf-onum:data-instance-from-template" {
    description
      "R/O hardware augments for an ONU instance from template.";
    uses bbf-hwc:hardware-config {
      refine "hardware" {
        config false;
      }
      refine "hardware/component/state" {
        if-feature "hardware-state";
      }
      augment "hardware" {
        description
          "Augments the 'hardware' container.";
        uses bbf-hwc:hardware-config-false;
      }
      augment "hardware/component" {
        description
          "Augments an element in the hardware component's list.";
        uses bbf-hwc:hardware-component-config-false {
          refine "physical-index" {
            if-feature "entity-mib";
          }
          refine "sensor-data" {
            if-feature "hardware-sensor";
          }
        }
      }
      augment "hardware/component/state" {
        description
          "Augments the hardware component's 'state' container.";
        uses bbf-hwc:hardware-component-state-config-false;
      }
    }
    notification hardware-state-change {
      description
        "A hardware-state-change notification is generated when the
         value of /hardware/last-change changes in the operational
         state.";
      reference
        "RFC 6933: Entity MIB (Version 4) - entConfigChange";
    }
  }
}
