module bbf-onu-ip-lower-layer {
  yang-version 1.1;
  namespace "urn:bbf:yang:bbf-onu-ip-lower-layer";
  prefix bbf-onu-ip-ll;

  import bbf-onus {
    prefix bbf-onus;
  }
  import bbf-onu-management {
    prefix bbf-onum;
  }
  import bbf-onu-interfaces {
    prefix bbf-onu-if;
  }
  import bbf-onu-if-type {
    prefix bbf-onuift;
  }

  organization
    "Broadband Forum <https://www.broadband-forum.org>
     Common YANG Work Area";
  contact
    "Comments or questions about this Broadband Forum YANG module
     should be directed to <mailto:help@broadband-forum.org>.

     Editor:      Joey Boyd, Adtran

     Editor:      Robert Peschi, Nokia

     PS Leader:   Joey Boyd, Adtran

     WA Director: Marta Seda, Calix";
  description
    "This module contains a collection of YANG definitions for
     supporting the Broadband Forum requirements on the management of
     Optical Network Units (ONUs).

     Specifically, this module augments an Optical Network Unit (ONU)
     IP interface with a reference to its lower layer interface.

     This module is based on definitions provided in:
     - module bbf-ip-interfaces.yang, revision 2024-11-11, TR-383
       Amendment 8

     Copyright (c) 2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-505; see the WT
     itself for full legal notices.";

  revision 2025-08-20 {
    description
      "TBD
       * Approval Date:    TBD.
       * Publication Date: TBD.";
    reference
      "TBD";
  }

  augment "/bbf-onus:onus/bbf-onum:onu/bbf-onum:data-stand-alone-instance/bbf-onu-if:interfaces/bbf-onu-if:interface" {
    description
      "Intended for a stand-alone ONU instance (i.e., that does not
       rely on any template).

       Adds to an IP interface a reference pointing to its
       lower-layer interface.";
    container ipif-lower-layer {
      presence "When present, provides the lower-layer within the interface
       stack.";
      description
        "Data node to provide linkage between a Layer 3 IP host
         interface and its lower-layer, i.e. Layer 2, interface. This
         is necessary when the Layer 3 IP host interface is an
         interface that is managed independently of its lower-layer
         interface. Alternatively, the interface providing Layer 2
         connectivity, e.g., Layer 2 termination or VLAN
         sub-interface, may also simultaneously support the Layer 3
         IP host management via IPv4 and/or IPv6, meaning that this
         lower-layer configuration is not relevant.";
      leaf interface {
        type leafref {
          path "../../../bbf-onu-if:interface/bbf-onu-if:name";
        }
        must "derived-from-or-self(current()/../../../bbf-onu-if:interface[bbf-onu-if:name= current()]/bbf-onu-if:type,'bbf-onuift:l2-termination') or derived-from-or-self(current()/../../../bbf-onu-if:interface[bbf-onu-if:name= current()]/bbf-onu-if:type,'bbf-onuift:vlan-sub-interface')" {
          error-message
            "The lower-layer of an IP interface interface is not a 'l2-termination', nor a 'vlan-sub-interface'.";
          description
            "Only allow Layer 2 termination or VLAN sub-interfaces
             as lower-layer for an IP interface.";
        }
        mandatory true;
        description
          "References the lower-layer interface.";
      }
    }
  }
  augment "/bbf-onus:onus/bbf-onum:onu/bbf-onum:data-instance-from-template/bbf-onu-if:interfaces/bbf-onu-if:interface" {
    description
      "Intended for an ONU instance derived from template(s).

       Adds to an IP interface a reference pointing to its
       lower-layer interface.";
    container ipif-lower-layer {
      presence "When present, provides the lower-layer of an IP interface
       within the interface stack.";
      description
        "Data node to provide linkage between a Layer 3 IP host
         interface and its lower-layer, i.e. Layer 2, interface. This
         is necessary when the Layer 3 IP host interface is an
         interface that is managed independently of its lower-layer
         interface. Alternatively, the interface providing Layer 2
         connectivity, e.g., Layer 2 termination or VLAN
         sub-interface, may also simultaneously support the Layer 3
         IP host management via IPv4 and/or IPv6, meaning that this
         lower-layer configuration is not relevant.";
      leaf interface {
        type leafref {
          path "../../../bbf-onu-if:interface/bbf-onu-if:name";
        }
        must "derived-from-or-self(current()/../../../bbf-onu-if:interface[bbf-onu-if:name= current()]/bbf-onu-if:type,'bbf-onuift:l2-termination') or derived-from-or-self(current()/../../../bbf-onu-if:interface[bbf-onu-if:name= current()]/bbf-onu-if:type,'bbf-onuift:vlan-sub-interface')" {
          error-message
            "The lower-layer of an IP interface interface is not a 'l2-termination', nor a 'vlan-sub-interface'.";
          description
            "Only allow Layer 2 termination or VLAN sub-interfaces
             as lower-layer for an IP interface.";
        }
        mandatory true;
        description
          "References the lower-layer interface.";
      }
    }
  }
  augment "/bbf-onus:onus/bbf-onum:template/bbf-onum:data/bbf-onu-if:interfaces/bbf-onu-if:interface" {
    description
      "Intended for an ONU template.

       Adds to an IP interface a reference pointing to its
       lower-layer interface.";
    container ipif-lower-layer {
      presence "When present, provides the lower-layer within the interface
       stack.";
      description
        "Intended for an ONU template.

         Data node to provide linkage between a Layer 3 IP host
         interface and its lower-layer, i.e. Layer 2, interface. This
         is necessary when the Layer 3 IP host interface is an
         interface that is managed independently of its lower-layer
         interface. Alternatively, the interface providing Layer 2
         connectivity, e.g., Layer 2 termination or VLAN
         sub-interface, may also simultaneously support the Layer 3
         IP host management via IPv4 and/or IPv6, meaning that this
         lower-layer configuration is not relevant.";
      leaf interface {
        type leafref {
          path "../../../bbf-onu-if:interface/bbf-onu-if:name";
        }
        must "derived-from-or-self(current()/../../../bbf-onu-if:interface[bbf-onu-if:name= current()]/bbf-onu-if:type,'bbf-onuift:l2-termination') or derived-from-or-self(current()/../../../bbf-onu-if:interface[bbf-onu-if:name= current()]/bbf-onu-if:type,'bbf-onuift:vlan-sub-interface')" {
          error-message
            "The lower-layer of an IP interface interface is not a 'l2-termination', nor a 'vlan-sub-interface'.";
          description
            "Only allow Layer 2 termination or VLAN sub-interfaces
             as lower-layer for an IP interface.";
        }
        mandatory true;
        description
          "References the lower-layer interface.";
      }
    }
  }
}
