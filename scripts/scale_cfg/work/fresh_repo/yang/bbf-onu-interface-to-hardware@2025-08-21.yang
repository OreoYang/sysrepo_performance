module bbf-onu-interface-to-hardware {
  yang-version 1.1;
  namespace "urn:bbf:yang:bbf-onu-interface-to-hardware";
  prefix bbf-onu-if-hw;

  import bbf-onus {
    prefix bbf-onus;
  }
  import bbf-onu-management {
    prefix bbf-onum;
  }
  import bbf-onu-interfaces {
    prefix bbf-onu-if;
  }
  import bbf-onu-hardware {
    prefix bbf-onu-hw;
  }
  import iana-hardware {
    prefix ianahw;
  }

  organization
    "Broadband Forum <https://www.broadband-forum.org>
     Common YANG Work Area";
  contact
    "Comments or questions about this Broadband Forum YANG module
     should be directed to <mailto:help@broadband-forum.org>.

     Editor:      Joey Boyd, Adtran

     Editor:      Robert Peschi, Nokia

     PS Leader:   Joey Boyd, Adtran

     WA Director: Marta Seda, Calix";
  description
    "This module contains a collection of YANG definitions for
     supporting the Broadband Forum requirements on the management of
     Optical Network Units (ONUs).

     Specifically, this module augments the ONU management interfaces
     model to enable interfaces to reference hardware components.

     This module is based on definitions provided in:
     - bbf-hardware.yang, TR-383 Amendment 5.

     Copyright (c) 2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-505; see the WT
     itself for full legal notices.";

  revision 2025-08-21 {
    description
      "TBD
       * Approval Date:    TBD.
       * Publication Date: TBD.";
    reference
      "TBD";
  }

  augment "/bbf-onus:onus/bbf-onum:onu/bbf-onum:data-stand-alone-instance/bbf-onu-if:interfaces/bbf-onu-if:interface" {
    description
      "Intended for a stand-alone ONU instance (i.e., that does not
       rely on any template).

       Only applicable for interfaces which need a reference to a
       hardware component. It usually applies to interfaces that are
       at the bottom of an interface stack.";
    container hardware-component {
      presence "The presence of this container enables management of hardware
       components relative to an interface.";
      description
        "Interface data nodes related to hardware components.";
      leaf-list port-layer-if {
        type leafref {
          path "../../../../bbf-onu-hw:hardware/bbf-onu-hw:component/bbf-onu-hw:name";
        }
        must "derived-from-or-self (current()/../../../../bbf-onu-hw:hardware/bbf-onu-hw:component[bbf-onu-hw:name=current()]/bbf-onu-hw:class, 'ianahw:port')" {
          error-message
            "The class of the referenced hardware component is neither derived from nor equal to 'port'.";
          description
            "An interface shall be associated to a hardware port
             component, i.e., a component with the 'class' 'port' or
             with the class an identity that is derived from a
             'port'.";
        }
        min-elements 1;
        description
          "A list of references to the physical port components
           corresponding to this interface. For system controlled
           interfaces, this relationship may also be system controlled
           and not able to be modified.";
      }
    }
  }
  augment "/bbf-onus:onus/bbf-onum:onu/bbf-onum:data-instance-from-template/bbf-onu-if:interfaces/bbf-onu-if:interface" {
    description
      "Intended for an ONU instance derived from template(s).

       Only applicable for interfaces which need a reference to a
       hardware component. It usually applies to interfaces that are
       at the bottom of an interface stack.";
    container hardware-component {
      presence "The presence of this container enables management of hardware
       components relative to an interface.";
      description
        "Interface data nodes related to hardware components.";
      leaf-list port-layer-if {
        type leafref {
          path "../../../../bbf-onu-hw:hardware/bbf-onu-hw:component/bbf-onu-hw:name";
        }
        must "derived-from-or-self (current()/../../../../bbf-onu-hw:hardware/bbf-onu-hw:component[bbf-onu-hw:name=current()]/bbf-onu-hw:class, 'ianahw:port')" {
          error-message
            "The class of the referenced hardware component is neither derived from nor equal to 'port'.";
          description
            "An interface shall be associated to a hardware port
             component, i.e., a component with the 'class' 'port' or
             with the class an identity that is derived from a
             'port'.";
        }
        min-elements 1;
        description
          "A list of references to the physical port components
           corresponding to this interface. For system controlled
           interfaces, this relationship may also be system controlled
           and not able to be modified.";
      }
    }
  }
  augment "/bbf-onus:onus/bbf-onum:template/bbf-onum:data/bbf-onu-if:interfaces/bbf-onu-if:interface" {
    description
      "Intended for an ONU template.

       Only applicable for interfaces which need a reference to a
       hardware component. It usually applies to interfaces that are
       at the bottom of an interface stack.";
    container hardware-component {
      presence "The presence of this container enables management of hardware
       components relative to an interface.";
      description
        "Interface data nodes related to hardware components.";
      leaf-list port-layer-if {
        type leafref {
          path "../../../../bbf-onu-hw:hardware/bbf-onu-hw:component/bbf-onu-hw:name";
        }
        must "derived-from-or-self (current()/../../../../bbf-onu-hw:hardware/bbf-onu-hw:component[bbf-onu-hw:name=current()]/bbf-onu-hw:class, 'ianahw:port')" {
          error-message
            "The class of the referenced hardware component is neither derived from nor equal to 'port'.";
          description
            "An interface shall be associated to a hardware port
             component, i.e., a component with the 'class' 'port' or
             with the class an identity that is derived from a
             'port'.";
        }
        min-elements 1;
        description
          "A list of references to the physical port components
           corresponding to this interface. For system controlled
           interfaces, this relationship may also be system controlled
           and not able to be modified.";
      }
    }
  }
}
