module bbf-interfaces-statistics-management {
  yang-version 1.1;
  namespace "urn:bbf:yang:bbf-interfaces-statistics-management";
  prefix bbf-if-ctrs;

  import ietf-interfaces {
    prefix if;
  }
  import ietf-yang-types {
    prefix yang;
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     WA Director: Joey Boyd, ADTRAN

     WA Director: Sven Ooghe, Nokia";
  description
    "This module contains a collection of YANG definitions for
     supporting the Broadband Forum requirements on interface
     management as applicable to access network equipment. As such,
     this module is specific to access network equipment (e.g.,
     BBF-specified Access Nodes and FTTdp DPUs).

     Specifically, this module augments ietf-interfaces with a reset
     action for statistics.

     Copyright (c) 2017-2022, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a5; see
     the TR itself for full legal notices.";

  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }
  revision 2021-06-02 {
    description
      "Amendment 4.
       * Approval Date:    2021-06-02.
       * Publication Date: 2021-06-02.";
    reference
      "TR-383a4: Common YANG Modules
                 <https://www.broadband-forum.org/technical/download/
                          TR-383_Amendment-4.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }
  revision 2018-07-13 {
    description
      "Amendment 1.
       * Approval Date:    2018-06-04.
       * Publication Date: see revision date above.";
    reference
      "TR-383: Common YANG Modules
               <https://www.broadband-forum.org/technical/download/
                        TR-383_Amendment-1.pdf>";
  }
  revision 2017-05-08 {
    description
      "Initial revision.
       * Approval Date:    see revision date above.
       * Publication Date: 2017-06-02.";
    reference
      "TR-383: Common YANG Modules
               <https://www.broadband-forum.org/technical/download/
                        TR-383.pdf>";
  }

  feature total-pkts {
    description
      "Indicates support for reporting the total transmitted and
       received packets on an interface.";
  }

  feature interface-statistics-configuration {
    description
      "Indicates support for configuration used for accumulating
       statistics per interface.";
  }

  feature interface-statistics-accumulation {
    description
      "Indicates support for managing the accumulation of statistics
       per interface.";
  }

  augment "/if:interfaces/if:interface" {
    if-feature "interface-statistics-configuration";
    description
      "Augment the 'interface' list with statistics configuration.";
    leaf statistics-accumulation {
      if-feature "interface-statistics-accumulation";
      type enumeration {
        enum "enable" {
          description
            "Enable accumulation of statistics that are reported
             under '/if:interfaces-state/if:interface/if:statistics'.

             Note that some interfaces may not accumulate certain
             types of statistics due to limitations associated
             with the hardware and/or type of interface. However,
             accumulation set to 'enable' means that all possible
             statistics will be provided, i.e., there is not any
             device condition in which the non-provided statistics can
             be provided.";
        }
        enum "disable" {
          description
            "Disable accumulation of statistics that are reported
             under '/if:interfaces-state/if:interface/if:
             statistics'.";
        }
        enum "system-conditional" {
          description
            "Enable the potential to accumulate statistics that are
             reported under '/if:interfaces-state/if:interface/if:
             statistics'. However, accumulation may not be possible
             depending on the current state of the system. For
             example, hardware resources used for statistics may be
             exhausted.

             Note that some interfaces may not accumulate certain
             types of statistics due to limitations associated
             with the hardware and/or type of interface.

             Note that accumulation of statistics on an interface
             in this state is under control of the system with no
             guarantee as to which statistics, if any, are
             accumulating. Further, the level of accumulation may
             change over time depending on the current state of the
             system. For example, explicit enabling of statistic
             accumulation on one or more interfaces may cause the
             system to shift resources as to fully support
             explicitly enabled interfaces while reducing the amount
             of accumulation support on an interface when set to
             'system-conditional'.";
        }
      }
      default "system-conditional";
      description
        "Configuration that controls the accumulation of statistics
         for this interface.";
    }
  }
  augment "/if:interfaces-state/if:interface" {
    description
      "The 'interfaces' list in the 'interfaces-state' container
       contains counters, grouped in the container 'statistics'.
       This augment provides the action to reset these
       counters.";
    action reset-statistics {
      description
        "When this action is invoked, the counters of this
         interface which are defined and/or augmented to the
         container '/if:interfaces-state/if:interface/if:statistics'
         are cleared.";
    }
  }

  augment "/if:interfaces-state/if:interface/if:statistics" {
    description
      "Augment the interface statistics with additional counters.";
    leaf in-pkts {
      if-feature "bbf-if-ctrs:total-pkts";
      type yang:counter64;
      description
        "The total number of packets received on the interface.";
    }
    leaf out-pkts {
      if-feature "bbf-if-ctrs:total-pkts";
      type yang:counter64;
      description
        "The total number of packets transmitted out of the
         interface.";
    }
    leaf accumulating {
      if-feature "interface-statistics-accumulation";
      type boolean;
      description
        "If true, statistics are accumulating on this interface.

         Note that some interfaces may not accumulate certain
         types of statistics due to limitations associated
         with the hardware and/or type of interface.";
    }
  }
}
