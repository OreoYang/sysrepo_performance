module bbf-l2-forwarding-shared-fdb {
  yang-version 1.1;
  namespace "urn:bbf:yang:bbf-l2-forwarding-shared-fdb";
  prefix bbf-l2-sfdb;

  import ietf-interfaces {
    prefix if;
  }
  import bbf-l2-forwarding {
    prefix bbf-l2-fwd;
  }

  organization
    "Broadband Forum <https://www.broadband-forum.org>
     Common YANG Work Area";
  contact
    "Comments or questions about this Broadband Forum YANG module
     should be directed to <mailto:help@broadband-forum.org>.

     Editor:      Nick Hancock, ADTRAN

     Editor:      Ludwig Pauwels, Nokia

     PS Leader:   Joey Boyd, ADTRAN

     WA Director: Joey Boyd, ADTRAN

     WA Director: Sven Ooghe, Nokia";
  description
    "This module contains a collection of YANG definitions for
     supporting the Broadband Forum requirements on layer 2 forwarding
     as applicable to access network equipment. As such, this module
     is specific to access network equipment (e.g., BBF-specified
     Access Nodes and FTTdp DPUs).

     Specifically, this module contains a collection of YANG
     definitions for managing shared forwarding databases.

     Copyright (c) 2017-2022, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383a5; see
     the TR itself for full legal notices.";

  revision 2022-03-01 {
    description
      "Amendment 5.
       * Approval Date:    2022-03-01.
       * Publication Date: 2022-03-01.";
    reference
      "TR-383a5: Common YANG Modules
                 <https://www.broadband-forum.org/technical/download/
                          TR-383_Amendment-5.pdf>";
  }
  revision 2020-10-13 {
    description
      "Amendment 3.
       * Approval Date:    2020-10-13.
       * Publication Date: 2020-10-13.";
    reference
      "TR-383a3: Common YANG Modules
                 <https://www.broadband-forum.org/technical/download/
                          TR-383_Amendment-3.pdf>";
  }
  revision 2018-12-03 {
    description
      "Amendment 2.
       * Approval Date:    2018-12-03.
       * Publication Date: 2018-12-03.";
    reference
      "TR-383a2: Common YANG Modules
               <https://www.broadband-forum.org/technical/download/
                        TR-383_Amendment-2.pdf>";
  }
  revision 2018-07-13 {
    description
      "Amendment 1.
       * Approval Date:    2018-06-04.
       * Publication Date: see revision date above.";
    reference
      "TR-383: Common YANG Modules
               <https://www.broadband-forum.org/technical/download/
                        TR-383_Amendment-1.pdf>";
  }

  grouping ethernet-interface {
    description
      "This grouping is use by data models that need to reference
       configured interfaces that are transporting Ethernet frames.";
    leaf interface {
      type if:interface-ref;
      description
        "References an interface transporting Ethernet frames.";
    }
  }

  grouping ethernet-interface-state {
    description
      "This grouping is use by data models that need to reference the
       operationally present interfaces that are transporting Ethernet
       frames.";
    leaf interface {
      type if:interface-state-ref;
      description
        "References an interface transporting Ethernet frames.";
    }
  }

  augment "/bbf-l2-fwd:forwarding/bbf-l2-fwd:forwarding-databases/bbf-l2-fwd:forwarding-database/bbf-l2-fwd:static-mac-address/bbf-l2-fwd:learning-constraint/bbf-l2-fwd:allowed-to-learn-on/bbf-l2-fwd:allow-to-learn-on" {
    if-feature "bbf-l2-fwd:forwarding-databases and
     bbf-l2-fwd:mac-learning";
    description
      "Augments the forwarding database static MAC address
       configuration with a case to specify that the MAC address is
       allowed to learn on one of a list of Ethernet interfaces. This
       case is relevant when shared forwarding databases are used.";
    case ethernet-interfaces {
      if-feature "bbf-l2-fwd:shared-forwarding-databases";
      container interface-references {
        description
          "The reference to a list of interfaces that are transporting
           Ethernet frames, the MAC address can be learned on any of
           these interfaces.";
        leaf-list interface {
          type if:interface-ref;
          description
            "References an interface transporting Ethernet frames.";
        }
      }
    }
  }
  augment "/bbf-l2-fwd:forwarding/bbf-l2-fwd:forwarding-databases/bbf-l2-fwd:forwarding-database/bbf-l2-fwd:static-mac-address/bbf-l2-fwd:learning-constraint/bbf-l2-fwd:install-in-fdb-on/bbf-l2-fwd:install-on" {
    if-feature "bbf-l2-fwd:forwarding-databases";
    description
      "Augments the forwarding database static MAC address
       configuration with a case to specify that the MAC address is
       statically assigned to a configured Ethernet interfaces. This
       case is relevant when shared forwarding databases are used.";
    case static-ethernet-interface {
      if-feature "bbf-l2-fwd:shared-forwarding-databases";
      container static-interface-reference {
        description
          "The reference to an interface transporting Ethernet frames
           on which the MAC address will be statically installed and
           as such affect the forwarding behavior immediately.";
        uses ethernet-interface;
      }
    }
  }
  augment "/bbf-l2-fwd:forwarding-state/bbf-l2-fwd:forwarding-databases/bbf-l2-fwd:forwarding-database/bbf-l2-fwd:mac-addresses/bbf-l2-fwd:mac-address/bbf-l2-fwd:learned-on" {
    if-feature "bbf-l2-fwd:forwarding-databases and
     bbf-l2-fwd:mac-learning";
    description
      "Augments the forwarding database state data with data per MAC
       address in case a shared forwarding database is used.";
    case interface {
      if-feature "bbf-l2-fwd:shared-forwarding-databases";
      uses ethernet-interface-state;
      list forwarder-ports {
        key "index";
        description
          "The list of forwarder-ports to which the forwarding is
           affected by learning the address on the interface. A
           forwarder-port is identified by identifying the forwarder
           and by identifying the port within this forwarder.";
        leaf index {
          type uint32;
          description
            "The index in the list of forwarder-ports.";
        }
        uses bbf-l2-fwd:forwarder-port-state;
      }
    }
  }
}
