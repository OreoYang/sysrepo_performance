module bbf-qos-traffic-mngt-profiles-common {
  yang-version 1.1;
  namespace "urn:bbf:yang:bbf-qos-traffic-mngt-profiles-common";
  prefix bbf-qos-tm-profc;

  import bbf-yang-types {
    prefix bbf-yang;
  }

  organization
    "Broadband Forum <https://www.broadband-forum.org>
     Common YANG Work Area";
  contact
    "Comments or questions about this Broadband Forum YANG module
     should be directed to <mailto:help@broadband-forum.org>.

     Editor:      Joey Boyd, Adtran

     Editor:      Robert Peschi, Nokia

     PS Leader:   Joey Boyd, Adtran

     WA Director: Marta Seda, Calix";
  description
    "This module contains a collection of YANG definitions for
     supporting the Broadband Forum requirements on the management of
     Optical Network Units (ONUs).

     Specifically, this module defines a set of profiles for QoS
     traffic management (TM).

     This module is based on definitions provided in:
     - bbf-qos-traffic-mngt.yang, TR-383 Amendment 6.

     Copyright (c) 2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-505; see the WT
     itself for full legal notices.";

  revision 2023-09-22 {
    description
      "TBD
       * Approval Date:    TBD.
       * Publication Date: TBD.";
    reference
      "TBD";
  }

  identity bac-type {
    description
      "Base identity of a Buffer Acceptance Control (BAC) type.";
  }

  identity taildrop {
    base bac-type;
    description
      "Taildrop BAC type.";
  }

  identity red {
    base bac-type;
    description
      "Random Early Detection (RED) BAC type.";
  }

  identity wtaildrop {
    base bac-type;
    description
      "Weighted taildrop BAC type.";
  }

  identity wred {
    base bac-type;
    description
      "Weighted Random Early Detection (WRED) BAC type.";
  }

  typedef queue-id {
    type uint32 {
      range "0..7";
    }
    description
      "An integer number identifying a queue within the context from
       which traffic will be scheduled. It is an abstract identifier:
       its value does NOT represent the priority of the queue itself.
       This 'queue-id' value is determined by means of a traffic class
       ID to queue ID mapping profile.";
  }

  typedef extended-scheduling-priority {
    type uint8 {
      range "0..15";
    }
    description
      "This number represents the priority of the queue or a scheduler
       competing with others in the context of scheduling traffic.
       Value 15 means highest priority and 0 means lowest priority.";
  }

  typedef extended-scheduling-weight {
    type uint16;
    description
      "If scheduling is to be performed from multiple queues or
       schedulers with the same priority, then the scheduling-weight
       assigns a weight to each of them.";
  }

  grouping min-threshold {
    description
      "Definition of minimum threshold.";
    leaf min-threshold {
      type bbf-yang:percent;
      description
        "The threshold from which the system begins to discard
         incoming frames in a random way.

         The value is a percentage to be calculated on the value of
         the leaf max-queue-size of the queue on which the BAC is
         applied.";
    }
  }

  grouping max-threshold {
    description
      "Definition of maximum threshold.";
    leaf max-threshold {
      type bbf-yang:percent;
      description
        "The threshold to discard all incoming frames.

         The value is a percentage to be calculated on the value of
         the leaf max-queue-size.";
    }
  }

  grouping max-probability {
    description
      "Definition of maximum probability.";
    leaf max-probability {
      type bbf-yang:percent;
      description
        "The maximum discard probability of frames before the
         maximum threshold is reached.";
    }
  }

  grouping common-random-early-detection-parameters {
    description
      "A set of parameters common to RED and WRED BAC algorithms.";
    uses min-threshold;
    uses max-threshold;
    uses max-probability;
  }

  grouping queues {
    description
      "Configuration data for queues.";
    list queue {
      key "local-queue-id";
      description
        "A queue.";
      leaf local-queue-id {
        type queue-id;
        description
          "The identification of a queue within the context of this
           list.";
      }
      choice queue-scheduling-cfg-type {
        description
          "Choice of queue scheduling types.";
        case inline {
          description
            "The queue parameters are directly configured here.";
          leaf priority {
            type extended-scheduling-priority;
            description
              "The priority used to schedule frames from a queue or
               scheduler, relative to the priority assigned to other
               queues or schedulers that are defined in the same
               traffic scheduling context. For example the set of
               queues defined for a particular interface form the
               context for scheduling outgoing traffic to this
               interface.";
          }
          leaf extended-weight {
            type extended-scheduling-weight;
            description
              "Queues or schedulers that are defined in a particular
               context, e.g. queues defined to schedule outgoing
               traffic to an interface, can have the same priority.
               The weight defines the portion of traffic that will be
               taken from this queue or scheduler by comparing the
               weight of this queue or scheduler against the sum of
               the weights of all queues or schedulers with the same
               scope and the same priority.";
          }
        }
      }
    }
  }

  grouping tm-root {
    description
      "The root for traffic management data.
       Traffic management involves the following aspects:
       - the forwarding decision determined to egress a frame through
         an outgoing traffic container (which can be an interface).
       - the traffic container (which can be a bottleneck) is
         associated to a scheduler resolving the contention of
         different queues competing to access the traffic container.
       - so after the outgoing traffic container is determined, the
         system needs to determine in which queue of the traffic
         container the frame must be directed. This takes place based
         on the frame's traffic class by means of the traffic class ID
         to queue ID mapping concept.
       - at any time, the scheduler resolves which queue should
         deliver the next frame to the egress traffic container by
         looking at the scheduling-priority and scheduling-weight of
         each of queues.
       The tm-root represents the scheduling stage directly attached
       to the bottleneck resource (typically an interface).";
    container tm-root {
      presence "Indicates the interface supports queues. Interfaces that
       support queues are typically the lowest layer of an interface
       stack that is Ethernet frame aware.";
      description
        "The attributes of the root in the scheduling tree.";
      choice children-type {
        description
          "Choice of a tm-root's child data node types.";
      }
    }
  }
}
