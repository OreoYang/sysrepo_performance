module vecima-olt-subsys {
  yang-version 1.1;
  namespace "urn:vecima:yang:vecima-olt-subsys";
  prefix vcm-olt-ss;

  import vecima-common {
    prefix vcm-cmn;
  }
  import vecima-olt-common {
    prefix vcm-olt-cmn;
  }

  organization
    "Vecima Networks Inc.";
  contact
    "https://www.vecima.com";
  description
    "This YANG module defines the olt devices subsystems/applications
     and the ability to control the log messages generated by each
     subsystem. Each subsystem can further have logging areas
     classified into smaller sub sections/groups named as sources.";

  revision 2022-04-27 {
    description
      "Initial version.";
    reference
      "";
  }

  typedef log-src {
    type enumeration {
      enum "libtimer" {
        value 1;
        description
          "The libtimer enum value";
      }
      enum "libdpl" {
        value 2;
        description
          "The libdpl enum value";
      }
      enum "cfg" {
        value 3;
        description
          "The cfg enum value";
      }
      enum "app" {
        value 4;
        description
          "The app enum value";
      }
      enum "libyang" {
        value 5;
        description
          "The libyang enum value";
      }
      enum "sysrepo" {
        value 6;
        description
          "The sysrepo enum value";
      }
      enum "netconf" {
        value 7;
        description
          "The netconf enum value";
      }
      enum "omci-me-layer" {
        value 8;
        description
          "The omci-me-layer enum value";
      }
      enum "omci-transport" {
        value 9;
        description
          "The omci-transport enum value";
      }
      enum "omci-svc" {
        value 10;
        description
          "The omci-svc enum value";
      }
      enum "onu-mgmt" {
        value 11;
        description
          "The onu-mgmt enum value";
      }
      enum "dhcpr" {
        value 12;
        description
          "The dhcpr enum value";
      }
      enum "bal-api" {
        value 13;
        description
          "The bal-api enum value";
      }
      enum "bum" {
        value 22;
        description
          "The bum enum value";
      }
      enum "arpr" {
        value 23;
        description
          "The arp relay enum value";
      }
      enum "sav" {
        value 24;
        description
          "The sav enum value";
      }
      enum "ndrelay" {
        value 25;
        description
          "The neighbor discovery relay enum value";
      }
      enum "dhcp6r" {
        value 26;
        description
          "The dhcp6r enum value";
      }
    }
    description
      "Each subsystem log message can further be filtered on the
       sources.";
  }

  grouping logging-group {
    description
      "The logging group";
    leaf output {
      type vcm-cmn:log-output;
      description
        "The log output";
    }
    leaf burst {
      type uint32 {
        range "0|2..2000";
      }
      description
        "The log burst";
    }
    list source {
      key "name";
      description
        "The log source";
      leaf name {
        type log-src;
        description
          "Application source name.";
      }
      leaf severity {
        type vcm-cmn:log-severity;
        mandatory true;
        description
          "Logging severity level.";
      }
    }
  }

  grouping subsys-group {
    description
      "The subsys group";
    container ch {
      description
        "Call home subsystem";
      container logging {
        description
          "The subsys logging group";
        uses logging-group;
      }
    }
    container logsrv {
      description
        "Log server subsystem";
      container logging {
        description
          "The logsrv logging group";
        uses logging-group;
      }
    }
    container lag {
      description
        "LAG subsystem";
      container logging {
        description
          "The lag logging group";
        uses logging-group;
      }
    }
    container le {
      description
        "Log to EXC controller subsystem";
      container logging {
        description
          "The le logging group";
        uses logging-group;
      }
    }
    container hwmon {
      description
        "Hardware monitor subsystem";
      container logging {
        description
          "The hwmon logging group";
        uses logging-group;
      }
    }
    container node-mgr {
      description
        "Node manager subsystem";
      container logging {
        description
          "The node-mgr logging group";
        uses logging-group;
      }
    }
    container notif-mgr {
      description
        "Notification manager subsystem";
      container logging {
        description
          "The notify-mgr logging group";
        uses logging-group;
      }
    }
    container ntp-mgr {
      description
        "NTP config manager subsystem";
      container logging {
        description
          "The ntp-mgr logging group";
        uses logging-group;
      }
    }
    container polt {
      description
        "POLT subsystem";
      container logging {
        description
          "The polt logging group";
        uses logging-group;
      }
    }
    container ph {
      description
        "Protocol handler subsystem";
      container logging {
        description
          "The ph logging group";
        uses logging-group;
      }
    }
    container suppinfo {
      description
        "Support info manager subsystem";
      container logging {
        description
          "The suppinfo logging group";
        uses logging-group;
      }
    }
    container swm {
      description
        "Software management subsystem";
      container logging {
        description
          "The swm logging group";
        uses logging-group;
      }
    }
    container sysmon {
      description
        "System monitor subsystem";
      container logging {
        description
          "The sysmon logging group";
        uses logging-group;
      }
    }
    container led-mgr {
      description
        "LED manager subsystem";
      container logging {
        description
          "The led-mgr logging group";
        uses logging-group;
      }
    }
    container metrics-mgr {
      description
        "Metrics manager subsystem";
      container logging {
        description
          "The metric-mgr logging group";
        uses logging-group;
      }
    }
    container lldp-ctlr {
      description
        "LLDP controller subsystem";
      container logging {
        description
          "The lldp-ctlr logging group";
        uses logging-group;
      }
    }
  }

  container subsys {
    description
      "The subsys";
    uses subsys-group;
    uses vcm-olt-cmn:support-info-group;
  }
}
