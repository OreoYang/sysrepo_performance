module vecima-xpon {
  yang-version 1.1;
  namespace "urn:vecima:yang:vecima-xpon";
  prefix vcm-xpon;

  import ietf-yang-types {
    prefix yang;
  }
  import bbf-yang-types {
    prefix bbf-yang;
  }
  import bbf-xpon-types {
    prefix bbf-xpon-types;
  }
  import ietf-interfaces {
    prefix if;
  }
  import bbf-xpon {
    prefix bbf-xpon;
  }

  organization
    "Vecima Networks";
  contact
    "xgs-pon@vecima.com";
  description
    "Augment of module bbf-xpon.yang by Vecima Networks
     Copyright (c) 2024, Vecima Networks, All Right Reserved.";

  revision 2025-08-12 {
    description
      "Add support for ONU flapping";
    reference
      "";
  }
  revision 2024-11-13 {
    description
      "Initial revision.";
    reference
      "ITU-T G.Supplement 49: Rogue optical network unit (ONU)
       considerations.";
  }

  identity rogue-onu-type {
    description
      "This identity is used to indicate the rogue Optical Network
       Unit (ONU) type.";
  }

  identity permanent-laser-on {
    base rogue-onu-type;
    description
      "This identity is used to indicate that the rogue Optical
       Network Unit (ONU) type is permanent laser transmission no
       matter actived or deactivated.";
  }

  identity early-on-slow-off-laser {
    base rogue-onu-type;
    description
      "This identity is used to indicate that the rogue Optical
       Network Unit (ONU) type is early laser on or slow laser off of
       active ONUs.";
  }

  identity resource-conflict {
    base rogue-onu-type;
    description
      "This identity is used to indicate that the rogue Optical
       Network Unit (ONU) type is resource conflicting of active
       ONUs.";
  }

  identity rogue-onu-handle-action {
    description
      "This identity is used to indicate the handling action to
       these suspected rogue Optical Network Units (ONU).";
  }

  identity identify {
    base rogue-onu-handle-action;
    description
      "This identity is used to indicate that only identify the
       rogue Optical Network Unit (ONU), no further action will
       be taken.";
  }

  identity disable {
    base rogue-onu-handle-action;
    base onu-troubleshooting-action;
    description
      "This identity is used to signify that Optical Line Termination
       (OLT) will disable these suspected rogue Optical Network Units
       (ONU) and remain effective even after an ONU power cycle.";
  }

  identity rogue-onu-test-exec-mode {
    description
      "This identity is used to indicate the rogue Optical Network
       Unit (ONU) test executed mode.";
  }

  identity scheduled {
    base rogue-onu-test-exec-mode;
    description
      "This identity is used to indicate that rogue Optical Network
       Unit (ONU) test which is running in scheduled mode.";
  }

  identity on-demand {
    base rogue-onu-test-exec-mode;
    description
      "This identity is used to indicate that rogue Optical Network
       Unit (ONU) test which is running in on-demand mode.";
  }

  identity rogue-onu-test-exec-status {
    description
      "This identity is used to indicate the rogue Optical Network
       Unit (ONU) test executed status.";
  }

  identity completed {
    base rogue-onu-test-exec-status;
    description
      "This identity is used to indicate that the running rogue
       Optical Network Unit (ONU) test was completed successfully.";
  }

  identity stopped {
    base rogue-onu-test-exec-status;
    description
      "This identity is used to indicate that the running rogue
       Optical Network Unit (ONU) test was intentionally stopped.";
  }

  identity terminated {
    base rogue-onu-test-exec-status;
    description
      "This identity is used to indicate that the running rogue
       Optical Network Unit (ONU) test was terminated by other
       higher priority test.";
  }

  identity interrupted {
    base rogue-onu-test-exec-status;
    description
      "This identity is used to indicate that the running rogue
       Optical Network Unit (ONU) test was interrupted due to the
       lower layer being out of service.";
  }

  identity aborted {
    base rogue-onu-test-exec-status;
    description
      "This identity is used to indicate that the new rogue Optical
       Network Unit (ONU) test (especially for scheduled mode) was
       aborted due to there has same or high priority test running.";
  }

  identity rogue-onu-test-trigger-method {
    description
      "This identity is used to indicate the trigger method of a rogue
       Optical Network Unit (ONU) test.";
  }

  identity periodic {
    base rogue-onu-test-trigger-method;
    description
      "This identity is used to indicate that a rogue Optical Network
       Unit (ONU) test will be triggered by periodic in scheduled
       mode.";
  }

  identity time-of-day {
    base rogue-onu-test-trigger-method;
    description
      "This identity is used to indicate that a rogue Optical Network
       Unit (ONU) test will be triggered by every 24 hours in
       scheduled mode.";
  }

  identity pon-los {
    base rogue-onu-test-trigger-method;
    description
      "This identity is used to indicate that a rogue Optical Network
       Unit (ONU) test will be triggered by a PON loss of signal in
       scheduled mode.";
  }

  identity onu-troubleshooting-action {
    description
      "This identity is used to indicate the troubleshooting will
       take to the Optical Network Unit (ONU).";
  }

  identity enable {
    base onu-troubleshooting-action;
    description
      "This identity is used to indicate that Optical Line Termination
       (OLT) will enable the Optical Network Unit (ONU).";
  }

  identity release {
    base onu-troubleshooting-action;
    description
      "This identity is used to indicate that Optical Line Termination
       (OLT) will release the auto quarantined Optical Network
       Unit (ONU).";
  }

  identity flap-onu-recover-method {
    description
      "This identity is used to indicate the suspected flapping
       Optical Network Unit (ONU) recover method.";
  }

  identity automatic {
    base flap-onu-recover-method;
    description
      "This identity is used to indicate that quarantined suspected
       flapping Optical Network Unit (ONU) will automatically
       recovered.";
  }

  identity manual {
    base flap-onu-recover-method;
    description
      "This identity is used to indicate that quarantined suspected
       flapping Optical Network Unit (ONU) will manually recovered.";
  }

  typedef action-status-type {
    type enumeration {
      enum "success" {
        description
          "The action executing was succeeded";
      }
      enum "fail" {
        description
          "The action executing was failed";
      }
    }
    description
      "Rogue Optical Network Unit (ONU) action executed status";
  }

  grouping rogue-onu-test-scheds-config-data {
    description
      "Configuration data intended for scheduled rogue Optical
       Network Unit (ONU) test.";
    container rogue-onu-test-scheds {
      description
        "Scheduled rogue Optical Network Unit (ONU) test
         configuration, and only one scheduled test can be enabled at
         the same time.";
      list rogue-onu-test-sched {
        key "name";
        unique "trigger-method";
        description
          "The list of scheduled rogue Optical Network Unit (ONU)
           test.";
        leaf name {
          type bbf-yang:string-ascii64;
          description
            "The name of the scheduled rogue Optical Network Unit
             (ONU) test.";
        }
        leaf type {
          type identityref {
            base rogue-onu-type;
          }
          mandatory true;
          description
            "The test type of the rogue Optical Network Unit (ONU)
             test.";
        }
        leaf conduct-action {
          type identityref {
            base rogue-onu-handle-action;
          }
          mandatory true;
          description
            "The action will conduct to these suspected rogue Optical
             Network Units (ONU) detected.";
        }
        leaf trigger-method {
          type identityref {
            base rogue-onu-test-trigger-method;
          }
          mandatory true;
          description
            "The trigger method of scheduled rogue Optical Network
             Unit (ONU) test.";
        }
        leaf periodic-interval {
          when "../vcm-xpon:trigger-method = 'vcm-xpon:periodic'" {
            description
              "The interval only valid for periodic trigger method.";
          }
          type uint16 {
            range "60..1440";
          }
          units "minutes";
          description
            "The interval of scheduled periodic rogue Optical Network
             Unit (ONU) test in minutes.";
        }
        leaf enabled {
          type boolean;
          default "false";
          description
            "This flag is used to enable/disable scheduled rogue
             Optical Network Unit (ONU) test.";
        }
      }
    }
  }

  grouping on-demand-rogue-onu-test-action-data {
    description
      "Configuration data intended for on-demand rogue Optical
       Network Unit (ONU) test.";
    action on-demand-rogue-onu-test {
      description
        "Action to start an on-demand rogue Optical Network Unit (ONU)
         test.";

      input {
        leaf name {
          type bbf-yang:string-ascii64;
          mandatory true;
          description
            "The name of the on-demand rogue Optical Network Unit
             (ONU) test.";
        }
        leaf type {
          type identityref {
            base rogue-onu-type;
          }
          mandatory true;
          description
            "The test type of the rogue Optical Network Unit (ONU)
             test.";
        }
        leaf conduct-action {
          type identityref {
            base rogue-onu-handle-action;
          }
          mandatory true;
          description
            "The mitigation action to these suspected rogue Optical
             Network Units (ONU) detected.";
        }
        leaf alloc-id {
          type uint16 {
            range "0..1020 | 1024..16383";
          }
          description
            "The alloc-id of the Optical Network Unit (ONU) to be
             executed rogue ONU testing.";
          reference
            "G.9807.1 section C.6.1.5.7";
        }
      }
      output {
        leaf rogue-onu-test-on-demand-status {
          type identityref {
            base bbf-xpon-types:action-request-status;
          }
          description
            "The status of the Optical Line Termination (OLT) handling
             the on-demand request.";
        }
        leaf rogue-onu-test-on-demand-reject-string {
          when "../rogue-onu-test-on-demand-status !=
           'bbf-xpon-types:request-being-processed'" {
            description
              "Only valid for Optical Line Termination (OLT) rejected
               the on-demand rogue Optical Network Unit (ONU) test
               request.";
          }
          type string;
          description
            "The text string indicating the reason why the Optical
             Line Termination (OLT) rejected the action.";
        }
      }
    }
  }

  grouping stop-rogue-onu-test-action-data {
    description
      "Configuration data intended for stop rogue Optical
       Network Unit (ONU) test.";
    action stop-rogue-onu-test {
      description
        "Action to stop the running rogue Optical Network Unit (ONU)
         test.";

      input {
        leaf name {
          type bbf-yang:string-ascii64;
          mandatory true;
          description
            "The name of the running rogue Optical Network Unit (ONU)
             test to be stopped.";
        }
      }
      output {
        leaf stop-rogue-onu-test-status {
          type identityref {
            base bbf-xpon-types:action-request-status;
          }
          description
            "The status of the Optical Line Termination (OLT)
             handling the stop request.";
        }
        leaf stop-rogue-onu-test-reject-string {
          when "../stop-rogue-onu-test-status !=
           'bbf-xpon-types:request-being-processed'" {
            description
              "Only valid for Optical Line Termination (OLT) rejected
               the stop rogue Optical Network Unit (ONU) test
               request.";
          }
          type string;
          description
            "The text string indicating the reason why the Optical
             Line Termination (OLT) rejected the action.";
        }
      }
    }
  }

  grouping troubleshoot-onu-action-data {
    description
      "Configuration data intended for troubleshooting suspected
       rogue Optical Network Unit (ONU).";
    action troubleshoot-onu {
      description
        "Action directly taking on the Optical Network Unit (ONU) via
         PLOAM message.";

      input {
        leaf onu-serial-number {
          type string {
            pattern '([a-zA-Z0-9]{4}[0-9a-fA-F]{8})?';
          }
          mandatory true;
          description
            "The serial number of the Optical Network Unit (ONU) to
             be troubleshot.";
          reference
            "ITU-T G.9807.1 section C.11.3.4.1.";
        }
        leaf action {
          type identityref {
            base onu-troubleshooting-action;
          }
          mandatory true;
          description
            "The action that Optical Line Termination (OLT) will send
             to Optical Network Unit (ONU) via PLOAM.";
        }
      }
      output {
        leaf troubleshoot-onu-status {
          type action-status-type;
          description
            "The status of the Optical Line Termination (OLT) handling
             the stop request.";
        }
        leaf troubleshoot-onu-reject-string {
          when "../troubleshoot-onu-status != 'success'" {
            description
              "Only valid for Optical Line Termination (OLT) rejected
               the Optical Network Unit (ONU) troubleshooting
               request.";
          }
          type string;
          description
            "The text string indicating the reason why the Optical
             Line Termination (OLT) rejected the action.";
        }
      }
    }
  }

  grouping rogue-onu-test-running-data {
    description
      "Data of running rogue Optical Network Unit (ONU) test.";
    list rogue-onu-test-running {
      key "name";
      config false;
      description
        "The list of the running scheduled or on-demand rogue Optical
         Network Unit (ONU) test.";
      leaf name {
        type bbf-yang:string-ascii64;
        description
          "The name of the running scheduled or on-demand rogue
           Optical Network Unit (ONU) test.";
      }
      leaf execute-mode {
        type identityref {
          base rogue-onu-test-exec-mode;
        }
        description
          "The mode of the running scheduled or on-demand rogue
           Optical Network Unit (ONU) test.";
      }
      leaf test-type {
        type identityref {
          base rogue-onu-type;
        }
        description
          "The test type of the rogue Optical Network Unit (ONU)
           test.";
      }
      leaf conduct-action {
        type identityref {
          base rogue-onu-handle-action;
        }
        description
          "The mitigation action to these suspected rogue Optical
           Network Units (ONU) detected.";
      }
      leaf alloc-id {
        type uint16 {
          range "0..1020 | 1024..16383";
        }
        description
          "The alloc-id of the Optical Network Unit (ONU) to be
           executed rogue ONU testing.";
        reference
          "G.9807.1 section C.6.1.5.7";
      }
      leaf start-time {
        type yang:date-and-time;
        description
          "The time that the running rogue Optical Network Unit (ONU)
           test started.";
      }
    }
  }

  grouping rogue-onu-test-report-data {
    description
      "Report data of rogue Optical Network Unit (ONU) test.";
    leaf name {
      type bbf-yang:string-ascii64;
      description
        "The name of the finished running scheduled or on-demand rogue
         Optical Network Unit (ONU) test.";
    }
    leaf execute-mode {
      type identityref {
        base rogue-onu-test-exec-mode;
      }
      description
        "The mode of the last running scheduled or on-demand rogue
         Optical Network Unit (ONU) test.";
    }
    leaf test-type {
      type identityref {
        base rogue-onu-type;
      }
      description
        "The test type of the rogue Optical Network Unit (ONU)
         test.";
    }
    leaf execute-status {
      type identityref {
        base rogue-onu-test-exec-status;
      }
      description
        "The executed status of the last running scheduled or
         on-demand rogue Optical Network Unit (ONU) test.";
    }
    leaf last-change {
      type yang:date-and-time;
      description
        "The time that the rogue Optical Network Unit (ONU) test
         report was last changed.";
    }
    container rogue-onus {
      description
        "Container of suspected rogue Optical Network Units (ONU).";
      list rogue-onu {
        key "serial-number";
        description
          "List of the suspected rogue Optical Network Units (ONU).";
        leaf serial-number {
          type string {
            pattern '([a-zA-Z0-9]{4}[0-9a-fA-F]{8})?';
          }
          description
            "The serial number of the suspected rogue Optical Network
             Units (ONU).";
          reference
            "ITU-T G.9807.1 section C.11.3.4.1.";
        }
        leaf onu-id {
          type uint32 {
            range "0..1020";
          }
          description
            "This is the TC layer ONU-ID identifier.";
          reference
            "ITU-T G.9807.1 section C.6.1.5.6.";
        }
        leaf v-ani-ref {
          type string;
          description
            "The v-ani interface of this suspected rogue Optical
             Network Unit (ONU).";
        }
        leaf type {
          type identityref {
            base rogue-onu-type;
          }
          description
            "The rogue Optical Network Unit (ONU) type.";
        }
        leaf action-conducted {
          type identityref {
            base rogue-onu-handle-action;
          }
          description
            "The mitigation action conducted to the Optical Network
             Unit (ONU).";
        }
      }
    }
  }

  grouping flap-onu-detect-config-data {
    description
      "Configuration data intended for flapping Optical Network Unit
       (ONU) detect.";
    container flap-onu-detect {
      description
        "Flapping Optical Network Unit (ONU) detect configuration.";
      leaf activate-interval {
        type uint32 {
          range "1..86400";
        }
        units "seconds";
        default "180";
        description
          "The Optical Network Unit (ONU) activate flapping detect
           window.";
      }
      leaf activate-event-threshold {
        type uint16 {
          range "2..10";
        }
        default "5";
        description
          "The activate flap events to generate an Optical Network
           Unit (ONU) flap.";
      }
      leaf power-change-interval {
        type uint32 {
          range "1..86400";
        }
        units "seconds";
        default "600";
        description
          "The Optical Network Unit (ONU) powering condition change
           flapping detect window.";
      }
      leaf power-change-event-threshold {
        type uint16 {
          range "2..10";
        }
        default "3";
        description
          "The powering condition change flap events to generate an
           Optical Network Unit (ONU) flap.";
      }
      leaf quarantine-interval {
        type uint32 {
          range "1..604800";
        }
        units "seconds";
        default "600";
        description
          "The interval to quarantine the suspected flapping Optical
           Network Unit (ONU).";
      }
      leaf recover-method {
        type identityref {
          base flap-onu-recover-method;
        }
        default "vcm-xpon:automatic";
        description
          "The method will conduct to the quarantined suspected
           flapping Optical Network Units (ONU) for recovery.";
      }
    }
  }

  augment "/if:interfaces/if:interface/bbf-xpon:channel-termination" {
    description
      "The configuration of rogue Optical Network Unit (ONU) test and
       flapping ONU detect.";
    uses rogue-onu-test-scheds-config-data;
    uses on-demand-rogue-onu-test-action-data;
    uses stop-rogue-onu-test-action-data;
    uses troubleshoot-onu-action-data;
    uses flap-onu-detect-config-data;
  }
  augment "/if:interfaces-state/if:interface/bbf-xpon:channel-termination" {
    description
      "The state data of rogue Optical Network Unit (ONU) test.";
    uses rogue-onu-test-running-data;
    container last-rogue-onu-test-report {
      config false;
      description
        "The report of last rogue Optical Network Unit (ONU) test.";
      uses rogue-onu-test-report-data;
    }
    leaf-list flap-affected-onus {
      if-feature "bbf-xpon:channel-termination-defects";
      type bbf-xpon-types:onu-serial-number;
      description
        "List of Optical Network Units (ONU) that have exhibited
         flapping behavior (repeated activation/deactivation or
         power changes).";
      reference
        "ONU flapping detection and quarantine system";
    }
    notification rogue-onu-test-report {
      description
        "Notification to report the result of rogue Optical Network
         Unit (ONU) test.";
      uses rogue-onu-test-report-data;
    }
  }
}
