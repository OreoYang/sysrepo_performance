module bbf-onu-ani-common {
  yang-version 1.1;
  namespace "urn:bbf:yang:bbf-onu-ani-common";
  prefix bbf-onuanic;

  organization
    "Broadband Forum <https://www.broadband-forum.org>
     Access Work Area";
  contact
    "Comments or questions about this Broadband Forum YANG module
     should be directed to <mailto:info@broadband-forum.org>.

     Editor:      Robert Peschi, Nokia

     PS Leader:   Joey Boyd, Adtran
                  Sven Ooghe, Nokia

     WA Director: Marta Seda, Calix
                  Herman Verbueken, Nokia";
  description
    "This module contains a collection of YANG definitions for
     supporting the Broadband Forum requirements on management of
     ITU-T Passive Optical Network (PON) interfaces as defined in
     ITU-T G.984.x, G.987.x, ITU-T G.989.x and ITU-T G.9807.x. As
     such, this module is specific to access network equipment (e.g.,
     BBF-specified Access Nodes and FTTdp DPUs).

     Specifically, this module defines features, identities and
     groupings for use when defining data nodes for managing
     interfaces of type ANI in ONU templates and ONU instances.

     Copyright (c) 2018-2025, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-505; see
     the WT itself for full legal notices.";

  revision 2026-12-03 {
    description
      "TBD.
       * Approval Date:    TBD.
       * Publication Date: TBD.";
    reference
      "TBD";
  }

  grouping back-pressure-config {
    description
      "Config data nodes to control backpressure to UNIs in case
       of upstream congestions in T-CONTs queues.";
    container back-pressure-to-unis {
      description
        "Controls the application of upstream back pressure to
         UNIs in case of upstream congestions in T-CONTs
         queues.";
      reference
        "ITU-T G.988 Clause 9.2.10";
      leaf enabled {
        type boolean;
        description
          "When 'true', enables the ONU to send back-pressure
           to its UNIs (e.g. by means of sending 'pause frames'
           to its Ethernet UNIs) when experiencing upstream
           congestion in its T-CONT queues. When 'false',
           disables the ONU to send back-pressure to its UNIs
           when experiencing upstream congestion in its T-CONT
           queues.";
        reference
          "ITU-T G.988 Clause 9.2.10 - Back pressure operation";
      }
      leaf duration {
        type uint32;
        description
          "Specifies the duration in microseconds of the
           back-pressure signal when applied to a UNI. It can
           be  used as a pause time for an Ethernet UNI. This
           data node is not applicable if back-pressure to UNIs
           is not enabled.";
        reference
          "ITU-T G.988 Clause 9.2.10 - Back pressure time";
      }
    }
  }
}
