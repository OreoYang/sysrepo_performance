module bbf-olt-vomci {
  yang-version 1.1;
  namespace "urn:bbf:yang:bbf-olt-vomci";
  prefix bbf-olt-vomci;

  import bbf-yang-types {
    prefix bbf-yang;
  }
  import bbf-vomci-types {
    prefix bbf-vomcit;
  }
  import bbf-network-function-client {
    prefix bbf-nfc;
  }
  import bbf-network-function-server {
    prefix bbf-nfs;
  }
  import bbf-network-function-endpoint-filter {
    prefix bbf-nf-epf;
  }
  import bbf-vomci-entity {
    prefix bbf-vomci-ent;
  }
  import bbf-xponvani {
    prefix bbf-xponvani;
  }
  import ietf-interfaces {
    prefix if;
  }

  organization
    "Broadband Forum <https://www.broadband-forum.org>
     SDN/NFV Work Area";
  contact
    "Comments or questions about this Broadband Forum YANG module
     should be directed to <mailto:help@broadband-forum.org>.

     Editor:      Tim Carey, Nokia

     Editor:      Dechao Zhang, China Mobile

     PS Leader:   Yves Hertoghs, VMWare

     WA Director: George Dobrowski, Morris Creek Consulting

     WA Director: Bruno Cornaglia, Vodafone";
  description
    "This module contains a collection of YANG definitions needed
     for a physical OLT's implementation of the vOMCI functionality
     as described in TR-451.

     Copyright (c) 2019-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2021-02-07 {
    description
      "Initial revision.";
    reference
      "TR-451: Section 5.3 OLT Description
               Section 5.2 vOMCI Function Description
               Section 5.6 vOMCI function to OLT Interface";
  }

  feature nf-client-supported {
    description
      "Indicates that client connectivity to network function's
       endpoints is supported.";
  }

  feature nf-server-supported {
    description
      "Indicates that server connectivity for network function's
       endpoints is supported.";
  }

  container remote-network-function {
    presence "Enables access to remote network functions";
    description
      "Remote network function (NF) configuration.";
    container nf-client {
      if-feature "bbf-olt-vomci:nf-client-supported";
      description
        "Client network function configuration.";
      leaf enabled {
        type boolean;
        default "true";
        description
          "Administratively enable the use of the client connectivity
           capability to the network function.";
      }
      uses bbf-nfc:nf-endpoint-grouping;
    }
    container nf-server {
      if-feature "bbf-olt-vomci:nf-server-supported";
      description
        "Server network function configuration.";
      leaf enabled {
        type boolean;
        default "true";
        description
          "Administratively enable the use of the server connectivity
           capability for connecting network function.";
      }
      uses bbf-nfs:nf-server-grouping;
    }
    container nf-endpoint-filter {
      description
        "The network function endpoint filter.";
      list rule {
        key "name";
        description
          "A rule contains a classification of resources that
           match a criteria. The result is an endpoint name.
           The definition is: first match, then stop searching
           for matches with other rules, obtain the resulting
           endpoint specified in this rule.";
        leaf name {
          type bbf-yang:string-ascii64;
          description
            "The rule name.";
        }
        leaf priority {
          type uint16 {
            range "1..max";
          }
          mandatory true;
          description
            "Indicates the priority for applying the match criteria
             of this rule against the priority of match criteria of
             other rules in this filter.

             The higher the value, the lower the priority, i.e.
             priority 1 is the highest priority.";
        }
        container flexible-match {
          description
            "Provides a generic framework to specify match criteria
             for endpoint filters. Specific match criteria shall be
             provided using augments in a context dependent way,
             e.g. match criteria can be augmented for ONUs, or in
             another context match criteria can be augmented for
             another resource.";
          uses bbf-nf-epf:onu-criteria-grouping;
        }
        leaf resulting-endpoint {
          type string;
          description
            "The resulting endpoint name.
             When operating as a server the resulting endpoint is a
             value in the listen-endpoint's remote-endpoint list.
             When operating as a client the resulting endpoint is a
             value in the client's remote-endpoint list.
             If operating as both a client and server to the same
             remote-endpoint which session to use (client or server)
             is unspecified as the information transmitted will reach
             the same remote-endpoint.";
        }
      }
    }
  }

  augment "/if:interfaces/if:interface/bbf-xponvani:v-ani" {
    description
      "This augmentation defines the configuration data to support
       vANI's that are managed using vOMCI.";
    container vomci-onu {
      description
        "This container provides the elements used for
         vOMCI configuration.";
      leaf vomci-func-remote-endpoint-name {
        type string;
        description
          "The remote endpoint name to use for transmitting vOMCI
           messages toward the vOMCI function as requested by the
           user. When configured, the entity takes precedence over
           the configured ONU remote endpoint filters";
      }
    }
  }
  augment "/if:interfaces-state/if:interface/bbf-xponvani:v-ani" {
    description
      "This augmentation defines the configuration data to support
       vANI's that are managed using vOMCI.";
    container vomci-onu-state {
      config false;
      description
        "vOMCI state for an ONU.
         For counters related to vOMCI messages:
           \"in-xxx\" counters are vOMCI messages received by the
           vOMCI function.
           \"out-xx\" counters are vOMCI messages send by the OLT
           to the vOMCI function.";
      leaf vomci-func-remote-endpoint-name {
        type string;
        description
          "The remote endpoint name associated with the ONU,
           regardless of the way it was assigned (e.g.,
           configuration, ONU filter).";
      }
      leaf vomci-func-communication-status {
        type identityref {
          base bbf-vomcit:vomci-communication-status;
        }
        description
          "The status of the vOMCI communication with the
           vOMCI function.";
      }
      uses bbf-vomci-ent:vomci-message-data;
    }
  }
}
