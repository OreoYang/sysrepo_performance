module bbf-onu-ethernet-interfaces {
  yang-version 1.1;
  namespace "urn:bbf:yang:bbf-onu-ethernet-interfaces";
  prefix bbf-onu-eth;

  import bbf-onu-management {
    prefix bbf-onum;
  }
  import bbf-onus {
    prefix bbf-onus;
  }
  import bbf-onu-interfaces {
    prefix bbf-onu-if;
  }
  import bbf-onu-if-type {
    prefix bbf-onuift;
  }
  import bbf-onu-ethernet-interfaces-common {
    prefix bbf-onuethifc;
  }

  organization
    "Broadband Forum <https://www.broadband-forum.org>
     Common YANG Work Area";
  contact
    "Comments or questions about this Broadband Forum YANG module
     should be directed to <mailto:help@broadband-forum.org>.

     Editor:      Joey Boyd, Adtran

     Editor:      Robert Peschi, Nokia

     PS Leader:   Joey Boyd, Adtran

     WA Director: Marta Seda, Calix";
  description
    "This module contains a collection of YANG definitions for
     supporting the Broadband Forum requirements on the management of
     Optical Network Units (ONUs).

     Specifically, this module defines data nodes for managing
     Ethernet interfaces. In this YANG module, 'Ethernet interface' is
     to be understood as referring to a 'IEEE Std 802.3 compliant
     Ethernet interface'.

     This module is based on definitions provided in:
     - ieee802-ethernet-interface.yang, revision 2019-06-21.

     Copyright (c) 2023, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of WT-505; see the WT
     itself for full legal notices.";

  revision 2024-08-22 {
    description
      "TBD
       * Approval Date:    TBD.
       * Publication Date: TBD.";
    reference
      "TBD";
  }

  feature ethernet-pfc {
    description
      "This device supports Ethernet priority flow-control.";
  }

  feature ethernet-pause {
    description
      "This device supports Ethernet PAUSE.";
  }

  augment "/bbf-onus:onus/bbf-onum:onu/bbf-onum:data-stand-alone-instance/bbf-onu-if:interfaces/bbf-onu-if:interface" {
    when "derived-from-or-self(bbf-onu-if:type,'bbf-onuift:ethernetCsmacd')" {
      description
        "Intended for a stand-alone ONU instance.

         Configuration augments that apply to all point-to-point
         Ethernet interfaces.";
    }
    description
      "Augment interface model with Ethernet interface specific
       configuration data nodes.";
    uses bbf-onuethifc:ethernet-config {
      refine "ethernet/cfg-rate-and-duplex" {
        default "rateauto-duplexauto";
      }
    }
  }
  augment "/bbf-onus:onus/bbf-onum:onu/bbf-onum:data-stand-alone-instance/bbf-onu-if:interfaces-state/bbf-onu-if:interface" {
    when "derived-from-or-self(bbf-onu-if:type,'bbf-onuift:ethernetCsmacd')" {
      description
        "Intended for a stand-alone ONU instance.

         State data augments that apply to all point-to-point
         Ethernet interfaces.";
    }
    description
      "Augment interface model with Ethernet interface specific
       state data nodes.";
    uses bbf-onuethifc:ethernet-state;
  }
  augment "/bbf-onus:onus/bbf-onum:onu/bbf-onum:data-instance-from-template/bbf-onu-if:interfaces/bbf-onu-if:interface" {
    when "derived-from-or-self(bbf-onu-if:type,'bbf-onuift:ethernetCsmacd')" {
      description
        "Intended for an ONU instance derived from template(s).

         Configuration augments that apply to all point-to-point
         Ethernet interfaces.";
    }
    description
      "Augment interface model with Ethernet interface specific
       configuration data nodes.";
    uses bbf-onuethifc:ethernet-config;
  }
  augment "/bbf-onus:onus/bbf-onum:onu/bbf-onum:data-instance-from-template/bbf-onu-if:interfaces-state/bbf-onu-if:interface" {
    when "derived-from-or-self(bbf-onu-if:type,'bbf-onuift:ethernetCsmacd')" {
      description
        "Intended for an ONU instance derived from template(s).

         State data augments that apply to all point-to-point
         Ethernet interfaces.";
    }
    description
      "Augment interface model with Ethernet interface specific
       state data nodes.";
    uses bbf-onuethifc:ethernet-state;
  }
  augment "/bbf-onus:onus/bbf-onum:template/bbf-onum:data/bbf-onu-if:interfaces/bbf-onu-if:interface" {
    when "derived-from-or-self(bbf-onu-if:type,'bbf-onuift:ethernetCsmacd')" {
      description
        "Applies to all P2P Ethernet interfaces.";
    }
    description
      "Intended for an ONU template.

       Augment interface model with Ethernet interface
       specific configuration nodes.";
    uses bbf-onuethifc:ethernet-config {
      refine "ethernet/cfg-rate-and-duplex" {
        default "rateauto-duplexauto";
      }
    }
  }
}
