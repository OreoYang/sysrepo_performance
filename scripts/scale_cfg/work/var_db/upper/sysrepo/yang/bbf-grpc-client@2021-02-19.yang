module bbf-grpc-client {
  yang-version 1.1;
  namespace "urn:bbf:yang:bbf-grpc-client";
  prefix bbf-grpc;

  organization
    "Broadband Forum <https://www.broadband-forum.org>
     SDN/NFV Work Area";
  contact
    "Comments or questions about this Broadband Forum YANG module
     should be directed to <mailto:help@broadband-forum.org>.

     Editor:      Tim Carey, Nokia

     Editor:      Dechao Zhang, China Mobile

     PS Leader:   Yves Hertoghs, VMWare

     WA Director: George Dobrowski, Morris Creek Consulting

     WA Director: Bruno Cornaglia, Vodafone";
  description
    "This module contains a collection of YANG definitions needed to
     communicate with gRPC servers as a client.

     Copyright (c) 2019-2021, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2021-02-19 {
    description
      "Initial revision.";
    reference
      "TR-451: Section 5.5 vOMCI Function to OLT Interface";
  }

  feature connection-backoff-supported {
    description
      "Indicates that the server supports configuring local
       bindings (i.e., the local address and local port) for
       TCP clients.";
  }

  grouping grpc-client-grouping {
    description
      "A reusable grouping for configuring a gRPC client,
       including the IP address and port number it initiates
       a connections to.

       Note that this grouping uses fairly typical descendent
       node names such that a stack of 'uses' statements will
       have name conflicts.  It is intended that the consuming
       data model will resolve the issue (e.g., by wrapping
       the 'uses' statement in a container called
       'grpc-client-parameters').  This model purposely does
       not do this itself so as to provide maximum flexibility
       to consuming models.";
    container channel {
      description
        "The gRPC channel properties.";
      leaf ping-interval {
        type uint32 {
          range "0..max";
        }
        units "seconds";
        default "300";
        description
          "Sets the amount of time after to send a ping request.
           A value of 0 disables pings from being sent.";
      }
    }
    container connection-backoff {
      if-feature "bbf-grpc:connection-backoff-supported";
      description
        "The connection backoff directs how a client
         reconnects to a remote endpoint, after discovering
         its connection to the remote endpoint has dropped.
         The gRPC connection backoff protocol is documented
         in github.com/grpc/grpc/blob/master/doc
                      /connection-backoff.md.";
      leaf initial-backoff {
        type uint16 {
          range "1..max";
        }
        units "seconds";
        default "30";
        description
          "The initial wait period after the first failure
           before retrying.";
      }
      leaf min-connect-timeout {
        type uint16 {
          range "1..max";
        }
        units "seconds";
        default "20";
        description
          "The minimum time to wait for the connection attempts.";
      }
      leaf multiplier {
        type decimal64 {
          fraction-digits 2;
        }
        default "1.60";
        description
          "The factor with which to multiply the backoff after a
           failed retry.";
      }
      leaf jitter {
        type decimal64 {
          fraction-digits 2;
        }
        default "0.20";
        description
          "The factor with which to randomizethe backoff.";
      }
      leaf max-backoff {
        type uint16 {
          range "1..max";
        }
        default "10";
        description
          "The number times the client tries to connect to a
           specific endpoint before moving on to the next endpoint
           in the list (round robin).";
      }
    }
  }
}
